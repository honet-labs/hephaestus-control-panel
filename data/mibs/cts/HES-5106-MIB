HES-5106-MIB DEFINITIONS ::= BEGIN

	IMPORTS
		enterprises, Counter, IpAddress         FROM RFC1155-SMI
		DisplayString, sysLocation              FROM RFC1213-MIB
		TRAP-TYPE                               FROM RFC-1215
		OBJECT-TYPE                             FROM RFC-1212
		ifIndex                                 FROM IF-MIB
		Counter64, Integer32                    FROM SNMPv2-SMI;

	cts OBJECT IDENTIFIER ::= { enterprises 9304 }

	PhysAddress ::=	OCTET STRING

	-- This data type is used to model media addresses.  For many
	-- types of media, this will be in a binary representation.
	-- For example, an ethernet address would be represented as
	-- a string of 6 octets.

	-- All representations of MAC addresses in this MIB Module use,
	-- as a textual convention (i.e., this convention does not affect
	-- their encoding), the data type:

	MacAddress ::= OCTET STRING (SIZE (6))      -- a 6 octet address in
	                                            -- the "canonical" order

	VLANPortMember ::= DisplayString (SIZE (0..27))

	swh
		OBJECT IDENTIFIER ::= { cts 100 }

	hes5106
		OBJECT IDENTIFIER ::= { swh 5106 }


-- Main

	swhSystemInformation
		OBJECT IDENTIFIER ::= { hes5106 1 }
	swhUserAuthentication
		OBJECT IDENTIFIER ::= { hes5106 2 }
	swhNetworkManagement
		OBJECT IDENTIFIER ::= { hes5106 3 }
	swhSwitchManagement
		OBJECT IDENTIFIER ::= { hes5106 4 }
	swhSwitchMonitor
		OBJECT IDENTIFIER ::= { hes5106 5 }
	swhSystemUtility
		OBJECT IDENTIFIER ::= { hes5106 6 }
	swhNewBootUpImage OBJECT-TYPE
		SYNTAX    INTEGER { image1(1), image2(2) }
		ACCESS    read-write
		STATUS    mandatory
		DESCRIPTION
			"New Boot Up Image"
		::= { hes5106 15 }
	swhSaveConfiguration OBJECT-TYPE
		SYNTAX    INTEGER { normal(0), save(1) }
		ACCESS    read-write
		STATUS    mandatory
		DESCRIPTION
			"Save Configuration to Flash ROM
			 set 1 to execute this function"
		::= { hes5106 7 }
	swhResetSystem OBJECT-TYPE
		SYNTAX    INTEGER { normal(0), reset(1) }
		ACCESS    read-write
		STATUS    mandatory
		DESCRIPTION
			"Reset System
			 set 1 to execute this function"
		::= { hes5106 8 }
	switchTraps OBJECT IDENTIFIER
		::= { hes5106 9 }


-- SystemInformation(1)

	swhCompanyInfo
		OBJECT IDENTIFIER ::= { swhSystemInformation 1 }
	swhHardwareInfo
		OBJECT IDENTIFIER ::= { swhSystemInformation 2 }


-- SystemInformation(1).CompanyInfo(1)

	swhCompanyName OBJECT-TYPE
		SYNTAX    DisplayString (SIZE (0..255))
		ACCESS    read-write
		STATUS    mandatory
		DESCRIPTION
			"Company Name"
		::= { swhCompanyInfo 1 }

	swhDHCPVendorID OBJECT-TYPE
		SYNTAX    DisplayString (SIZE (0..255))
		ACCESS    read-write
		STATUS    mandatory
		DESCRIPTION
			"DHCP Vendor ID"
		::= { swhCompanyInfo 7 }

	swhCLIHostname OBJECT-TYPE
		SYNTAX    DisplayString (SIZE (0..255))
		ACCESS    read-write
		STATUS    mandatory
		DESCRIPTION
			"CLI Hostname"
		::= { swhCompanyInfo 6 }


-- SystemInformation(1).HardwareInfo(2)

	swhModelName OBJECT-TYPE
		SYNTAX    DisplayString (SIZE (0..255))
		ACCESS    read-only
		STATUS    mandatory
		DESCRIPTION
			"Model Name"
		::= { swhHardwareInfo 1 }

	swhBootUpImage OBJECT-TYPE
		SYNTAX    DisplayString
		ACCESS    read-only
		STATUS    mandatory
		DESCRIPTION
			"Boot Up Image"
		::= { swhHardwareInfo 40 }

	swhNextBootUpImage OBJECT-TYPE
		SYNTAX    DisplayString
		ACCESS    read-only
		STATUS    mandatory
		DESCRIPTION
			"Next Boot Up Image"
		::= { swhHardwareInfo 41 }

	swhImage1FirmwareVersion OBJECT-TYPE
		SYNTAX    DisplayString (SIZE (0..255))
		ACCESS    read-only
		STATUS    mandatory
		DESCRIPTION
			"Image1 Firmware Version"
		::= { swhHardwareInfo 45 }

	swhImage2FirmwareVersion OBJECT-TYPE
		SYNTAX    DisplayString (SIZE (0..255))
		ACCESS    read-only
		STATUS    mandatory
		DESCRIPTION
			"Image2 Firmware Version"
		::= { swhHardwareInfo 46 }

--	swhCPLDVersion OBJECT-TYPE
--		SYNTAX    INTEGER
--		ACCESS    read-only
--		STATUS    mandatory
--		DESCRIPTION
--			"Case CPLD Version."
--		::= { swhHardwareInfo 55 }

	swhMBVersion OBJECT-TYPE
		SYNTAX    DisplayString (SIZE (0..255))
		ACCESS    read-only
		STATUS    mandatory
		DESCRIPTION
			"Main Board Version"
		::= { swhHardwareInfo 9 }

	swhSerialNumber OBJECT-TYPE
		SYNTAX    DisplayString (SIZE (0..255))
		ACCESS    read-only
		STATUS    mandatory
		DESCRIPTION
			"serial number of this device."
		::= { swhHardwareInfo 14 }

	swhDateCode OBJECT-TYPE
		SYNTAX    DisplayString (SIZE (0..255))
		ACCESS    read-only
		STATUS    mandatory
		DESCRIPTION
			"the day of producing this device"
		::= { swhHardwareInfo 15 }

	swhCPUTemperature OBJECT-TYPE
		SYNTAX    Integer32 (-2147483648..2147483647)
		ACCESS    read-only
		STATUS    mandatory
		DESCRIPTION
			"Current CPU Temperature(1/10)"
		::= { swhHardwareInfo 20 }

	swhPHY1Temperature OBJECT-TYPE
		SYNTAX    DisplayString
		ACCESS    read-only
		STATUS    mandatory
		DESCRIPTION
			"PHY1 Temperature(C)."
		::= { swhHardwareInfo 21 }

	swhPHY2Temperature OBJECT-TYPE
		SYNTAX    DisplayString
		ACCESS    read-only
		STATUS    mandatory
		DESCRIPTION
			"PHY2 Temperature(C)."
		::= { swhHardwareInfo 22 }

	swhPHY3Temperature OBJECT-TYPE
		SYNTAX    DisplayString
		ACCESS    read-only
		STATUS    mandatory
		DESCRIPTION
			"PHY3 Temperature(C)."
		::= { swhHardwareInfo 23 }

	swhFanState OBJECT-TYPE
		SYNTAX    DisplayString
		ACCESS    read-only
		STATUS    mandatory
		DESCRIPTION
			"Case fan State."
		::= { swhHardwareInfo 38 }

	swhPowerSupplyA OBJECT-TYPE
		SYNTAX    INTEGER { na(0), installed(1), not-installed(2) }
		ACCESS    read-only
		STATUS    mandatory
		DESCRIPTION
			"module a power supply exist or not"
		::= { swhHardwareInfo 24 }

	swhPowerSupplyAType OBJECT-TYPE
		SYNTAX    INTEGER { na(0), dc(1), ac(2) }
		ACCESS    read-only
		STATUS    mandatory
		DESCRIPTION
			"module a is dc or ac power supply"
		::= { swhHardwareInfo 25 }

	swhPowerSupplyAState OBJECT-TYPE
		SYNTAX    INTEGER { na(0), active(1), ng(2), ac-cut(3) }
		ACCESS    read-only
		STATUS    mandatory
		DESCRIPTION
			"module a power supply state"
		::= { swhHardwareInfo 26 }

	swhPowerSupplyB OBJECT-TYPE
		SYNTAX    INTEGER { na(0), installed(1), not-installed(2) }
		ACCESS    read-only
		STATUS    mandatory
		DESCRIPTION
			"module b power supply exist or not"
		::= { swhHardwareInfo 28 }

	swhPowerSupplyBType OBJECT-TYPE
		SYNTAX    INTEGER { na(0), dc(1), ac(2), battery(3) }
		ACCESS    read-only
		STATUS    mandatory
		DESCRIPTION
			"module b is dc or ac power supply"
		::= { swhHardwareInfo 29 }

	swhPowerSupplyBState OBJECT-TYPE
		SYNTAX    INTEGER { na(0), active(1), ng(2) }
		ACCESS    read-only
		STATUS    mandatory
		DESCRIPTION
			"module b power supply state"
		::= { swhHardwareInfo 30 }

-- SystemInformation(1).SoftwareInfo(3)


-- SystemInformation(1).CATVModuleInfo(5)


-- SystemInformation(1).BatteryModuleInfo(6)


-- UserAuthentication(2).UserTable(1)

	swhUserTable OBJECT-TYPE
		SYNTAX    SEQUENCE OF SwhUserEntry
		ACCESS    not-accessible
		STATUS    mandatory
		DESCRIPTION
			"Table of user information."
		::= { swhUserAuthentication 1 }

	-- Table Entry
	swhUserEntry OBJECT-TYPE
		SYNTAX    SwhUserEntry
		ACCESS    not-accessible
		STATUS    mandatory
		DESCRIPTION
			"An entry in the table, containing information
			about user.
			Only Administrator can read this table"
		INDEX    { swhUserIndex }
		::= { swhUserTable 1 }

	SwhUserEntry ::=
		SEQUENCE {
			swhUserIndex
				INTEGER,
		--	swhUserValid
		--		INTEGER,
			swhUserEnable
				INTEGER,
			swhUserName
				DisplayString,
			swhUserPassword
				DisplayString,
			swhUserDescription
				DisplayString,
		--	swhUserIPSecurity
		--		INTEGER,
		--	swhUserIPAddr
		--		IpAddress,
		--	swhUserIPTrapDest
		--		IpAddress,
			swhUserConsoleLevel
				INTEGER
		--	swhUserSNMPLevel
		--		INTEGER,
		--	swhUserWebLevel
		--		INTEGER
		}

	swhUserIndex OBJECT-TYPE
		SYNTAX    INTEGER (0..2147483647)
		ACCESS    not-accessible
		STATUS    mandatory
		DESCRIPTION
			"user index"
		::= { swhUserEntry 1 }

--	swhUserValid OBJECT-TYPE
--		SYNTAX    INTEGER { invalid(0), valid(1) }
--		ACCESS    read-only
--		STATUS    mandatory
--		DESCRIPTION
--			"Valid"
--		::= { swhUserEntry 2 }

	swhUserEnable OBJECT-TYPE
		SYNTAX    INTEGER { disable(0), enable(1) }
		ACCESS    read-only
		STATUS    mandatory
		DESCRIPTION
			"Enable"
		::= { swhUserEntry 3 }

	swhUserName OBJECT-TYPE
		SYNTAX    DisplayString (SIZE (0..255))
		ACCESS    read-only
		STATUS    mandatory
		DESCRIPTION
			"Name"
		::= { swhUserEntry 4 }

	swhUserPassword OBJECT-TYPE
		SYNTAX    DisplayString (SIZE (0..255))
		ACCESS    read-only
		STATUS    mandatory
		DESCRIPTION
			"Password"
		::= { swhUserEntry 5 }

	swhUserDescription OBJECT-TYPE
		SYNTAX    DisplayString (SIZE (0..255))
		ACCESS    read-only
		STATUS    mandatory
		DESCRIPTION
			"Description"
		::= { swhUserEntry 6 }

	--swhUserIPSecurity OBJECT-TYPE
	--	SYNTAX    INTEGER { disable(0), enable(1) }
	--	ACCESS    read-only
	--	STATUS    mandatory
	--	DESCRIPTION
	--		"IP Security enable,
	--		 only swhUserIPAddr could login console"
	--	::= { swhUserEntry 7 }

	--swhUserIPAddr OBJECT-TYPE
	--	SYNTAX    IpAddress
	--	ACCESS    read-only
	--	STATUS    mandatory
	--	DESCRIPTION
	--		"The IP address from which could login console."
	--	::= { swhUserEntry 8 }

	--swhUserIPTrapDest OBJECT-TYPE
	--	SYNTAX    IpAddress
	--	ACCESS    read-write
	--	STATUS    mandatory
	--	DESCRIPTION
	--		"SNMP trap destination IP address"
	--	::= { swhUserEntry 9 }

	swhUserConsoleLevel OBJECT-TYPE
		SYNTAX    INTEGER { readonly(1), readwrite(2), administrator(3) }
		ACCESS    read-only
		STATUS    mandatory
		DESCRIPTION
			"Console Level"
		::= { swhUserEntry 10 }

	--swhUserSNMPLevel OBJECT-TYPE
	--	SYNTAX    INTEGER { readonly(1), readwrite(2), administrator(3) }
	--	ACCESS    read-write
	--	STATUS    mandatory
	--	DESCRIPTION
	--		"SNMP Level"
	--	::= { swhUserEntry 11 }

	--swhUserWebLevel OBJECT-TYPE
	--	SYNTAX    INTEGER { readonly(1), readwrite(2), administrator(3) }
	--	ACCESS    read-write
	--	STATUS    mandatory
	--	DESCRIPTION
	--		"Web Level"
	--	::= { swhUserEntry 12 }


-- UserAuthentication(2).RADIUSConfiguration(2)

	swhRADIUSConfiguration
		OBJECT IDENTIFIER ::= { swhUserAuthentication 2 }

	swhRADIUSEncryption OBJECT-TYPE
		SYNTAX    INTEGER { disable(0), aes-128(2) }
		ACCESS    read-write
		STATUS    mandatory
		DESCRIPTION
			"Enable or disable RADIUS SecretKey Encryption."
		::= { swhRADIUSConfiguration 10 }

	swhRADIUSEn OBJECT-TYPE
		SYNTAX    INTEGER { disable(0), enable(1) }
		ACCESS    read-write
		STATUS    mandatory
		DESCRIPTION
			"Enable or disable RADIUS client."
		::= { swhRADIUSConfiguration 1 }

	swhRADIUSSecretKey OBJECT-TYPE
		SYNTAX    DisplayString
		ACCESS    read-write
		STATUS    mandatory
		DESCRIPTION
			"the plain code for encrypting data."
		::= { swhRADIUSConfiguration 2 }

	swhRADIUSPort OBJECT-TYPE
		SYNTAX    INTEGER (1025..65535)
		ACCESS    read-write
		STATUS    mandatory
		DESCRIPTION
			"RADIUS server port."
		::= { swhRADIUSConfiguration 3 }

	swhRADIUSRetry OBJECT-TYPE
		SYNTAX    INTEGER (0..2)
		ACCESS    read-write
		STATUS    mandatory
		DESCRIPTION
			"The retry times of connecting to an unknown RADIUS server."
		::= { swhRADIUSConfiguration 5 }

	swhRADIUSIPAddr OBJECT-TYPE
		SYNTAX    IpAddress 
		ACCESS    read-write
		STATUS    mandatory
		DESCRIPTION
			"RADIUS server ip address."
		::= { swhRADIUSConfiguration 6 }

	swhRADIUSIPAddr2 OBJECT-TYPE
		SYNTAX    IpAddress 
		ACCESS    read-write
		STATUS    mandatory
		DESCRIPTION
			"2th RADIUS server ip address."
		::= { swhRADIUSConfiguration 7 }

	swhRADIUSIPv6Addr OBJECT-TYPE
		SYNTAX    DisplayString (SIZE (0..255))
		ACCESS    read-write
		STATUS    mandatory
		DESCRIPTION
			"RADIUS server ipv6 address."
		::= { swhRADIUSConfiguration 8 }

	swhRADIUSIPv6Addr2 OBJECT-TYPE
		SYNTAX    DisplayString (SIZE (0..255))
		ACCESS    read-write
		STATUS    mandatory
		DESCRIPTION
			"2th RADIUS server ipv6 address."
		::= { swhRADIUSConfiguration 9 }


-- UserAuthentication(2).TACACSConfiguration(3)

--	swhTACACSConfiguration
--		OBJECT IDENTIFIER ::= { swhUserAuthentication 3 }
--
--	swhTACACSEn OBJECT-TYPE
--		SYNTAX    INTEGER { disable(0), enable(1) }
--		ACCESS    read-write
--		STATUS    mandatory
--		DESCRIPTION
--			"Enable or disable TACACS client."
--		::= { swhTACACSConfiguration 1 }
--
--	swhTACACSSecretKey OBJECT-TYPE
--		SYNTAX    DisplayString
--		ACCESS    read-write
--		STATUS    mandatory
--		DESCRIPTION
--			"the plain code for encrypting data."
--		::= { swhTACACSConfiguration 2 }
--
--	swhTACACSPort OBJECT-TYPE
--		SYNTAX    INTEGER (1025..65535)
--		ACCESS    read-write
--		STATUS    mandatory
--		DESCRIPTION
--			"TACACS server port."
--		::= { swhTACACSConfiguration 3 }
--
--	swhTACACSLease OBJECT-TYPE
--		SYNTAX    INTEGER (0..9999)
--		ACCESS    read-write
--		STATUS    mandatory
--		DESCRIPTION
--			"The valid period of a user account from TACACS server,
--			unit is seccond."
--		::= { swhTACACSConfiguration 4 }
--
--	swhTACACSRetry OBJECT-TYPE
--		SYNTAX    INTEGER (0..2)
--		ACCESS    read-write
--		STATUS    mandatory
--		DESCRIPTION
--			"The retry times of connecting to an unknown TACACS server."
--		::= { swhTACACSConfiguration 5 }
--
--	swhTACACSIPAddr OBJECT-TYPE
--		SYNTAX    IpAddress 
--		ACCESS    read-write
--		STATUS    mandatory
--		DESCRIPTION
--			"TACACS server ip address."
--		::= { swhTACACSConfiguration 6 }
--
--	swhTACACSIPAddr2 OBJECT-TYPE
--		SYNTAX    IpAddress 
--		ACCESS    read-write
--		STATUS    mandatory
--		DESCRIPTION
--			"2th TACACS server ip address."
--		::= { swhTACACSConfiguration 7 }
--
--	swhTACACSIPv6Addr OBJECT-TYPE
--		SYNTAX    DisplayString (SIZE (0..255))
--		ACCESS    read-write
--		STATUS    mandatory
--		DESCRIPTION
--			"TACACS server ipv6 address."
--		::= { swhTACACSConfiguration 8 }
--
--	swhTACACSIPv6Addr2 OBJECT-TYPE
--		SYNTAX    DisplayString (SIZE (0..255))
--		ACCESS    read-write
--		STATUS    mandatory
--		DESCRIPTION
--			"2th TACACS server ipv6 address."
--		::= { swhTACACSConfiguration 9 }


-- UserAuthentication(2).UserPasswordEncryption(4)

	swhUserPasswordEncryption OBJECT-TYPE
		SYNTAX    INTEGER { disable(0), md5(1), aes-128(2) }
		ACCESS    read-only
		STATUS    mandatory
		DESCRIPTION
			"Enable or disable Password Encryption."
		::= { swhUserAuthentication 4 }


-- NetworkManagement(3)

	swhNetworkConfiguration
		OBJECT IDENTIFIER ::= { swhNetworkManagement 1 }
	swhSystemServiceConfiguration
		OBJECT IDENTIFIER ::= { swhNetworkManagement 2 }
	swhRS232TelnetConsoleConfiguration
		OBJECT IDENTIFIER ::= { swhNetworkManagement 3 }
	swhTimeServerConfiguration
		OBJECT IDENTIFIER ::= { swhNetworkManagement 7 }
--	swhTimeRange
--		OBJECT IDENTIFIER ::= { swhNetworkManagement 10 }
	swhDeviceCommunity
		OBJECT IDENTIFIER ::= { swhNetworkManagement 4 }
	swhTrapDestination
		OBJECT IDENTIFIER ::= { swhNetworkManagement 5 }
	swhTrapConfiguration
		OBJECT IDENTIFIER ::= { swhNetworkManagement 6 }
	swhSyslogConfiguration
		OBJECT IDENTIFIER ::= { swhNetworkManagement 8 }


-- NetworkManagement(3).NetworkConfiguration(1)

	swhNetMacAddr OBJECT-TYPE
		SYNTAX    MacAddress
		ACCESS    read-only
		STATUS    mandatory
		DESCRIPTION
			"The media-dependent `physical' address."
		::= { swhNetworkConfiguration 1 }

	swhNetType OBJECT-TYPE
		SYNTAX    INTEGER { manual(1), dhcp(0) }
		ACCESS    read-write
		STATUS    mandatory
		DESCRIPTION
			"auto will get ip from DHCP"
		::= { swhNetworkConfiguration 2 }

	swhNetIPv4DHCPAutoRecycle OBJECT-TYPE
		SYNTAX    INTEGER { disable(0), enable(1) }
		ACCESS    read-write
		STATUS    mandatory
		DESCRIPTION
			"IPv4 DHCP Auto Recycle"
		::= { swhNetworkConfiguration 24 }

	swhNetIPv4DHCPAutoRecyclePortList OBJECT-TYPE
		SYNTAX    DisplayString (SIZE (0..255))
		ACCESS    read-write
		STATUS    mandatory
		DESCRIPTION
			"IPv4 DHCP Auto Recycle Port List."
		::= { swhNetworkConfiguration 25 }

	swhNetIPv4DHCPRecycle OBJECT-TYPE
		SYNTAX    INTEGER { normal(0), recycle(1) }
		ACCESS    read-write
		STATUS    mandatory
		DESCRIPTION
			"IPv4 DHCP Recycle"
		::= { swhNetworkConfiguration 23 }

	swhNetIPAddr OBJECT-TYPE
		SYNTAX    IpAddress
		ACCESS    read-write
		STATUS    mandatory
		DESCRIPTION
			"The IP address to which this entry's addressing
			 information pertains."
		::= { swhNetworkConfiguration 3 }

	swhNetIPMask OBJECT-TYPE
		SYNTAX    IpAddress
		ACCESS    read-write
		STATUS    mandatory
		DESCRIPTION
			"The subnet mask associated with the IP address of
			 this entry.  The value of the mask is an IP
			 address with all the network bits set to 1 and all
			 the hosts bits set to 0."
		::= { swhNetworkConfiguration 4 }

	swhNetGateway OBJECT-TYPE
		SYNTAX    IpAddress
		ACCESS    read-write
		STATUS    mandatory
		DESCRIPTION
			"Gateway"
		::= { swhNetworkConfiguration 5 }

	swhNetIPv4En OBJECT-TYPE
		SYNTAX    INTEGER { enable(1), disable(0) }
		ACCESS    read-write
		STATUS    mandatory
		DESCRIPTION
			"enable or disable IPv4 process."
		::= { swhNetworkConfiguration 8 }

	swhNetCurrentIPAddr OBJECT-TYPE
		SYNTAX    IpAddress
		ACCESS    read-only
		STATUS    mandatory
		DESCRIPTION
			"The Current IP address to which this entry's addressing
			 information pertains."
		::= { swhNetworkConfiguration 10 }

	swhNetCurrentIPMask OBJECT-TYPE
		SYNTAX    IpAddress
		ACCESS    read-only
		STATUS    mandatory
		DESCRIPTION
			"The Current subnet mask associated with the IP address of
			 this entry.  The value of the mask is an IP
			 address with all the network bits set to 1 and all
			 the hosts bits set to 0."
		::= { swhNetworkConfiguration 11 }

	swhNetCurrentGateway OBJECT-TYPE
		SYNTAX    IpAddress
		ACCESS    read-only
		STATUS    mandatory
		DESCRIPTION
			"Current Gateway"
		::= { swhNetworkConfiguration 12 }

--	swhNetDNSServerAuto OBJECT-TYPE
--		SYNTAX    INTEGER { manually(0), automatically(1) }
--		ACCESS    read-write
--		STATUS    mandatory
--		DESCRIPTION
--			"dns server 0: DNS Manually 1: DNS Automatically."
--		::= { swhNetworkConfiguration 47 }

--	swhNetDNSServerIPAddr OBJECT-TYPE
--		SYNTAX    IpAddress
--		ACCESS    read-write
--		STATUS    mandatory
--		DESCRIPTION
--			"dns server ip address."
--		::= { swhNetworkConfiguration 13 }

--	swhNetDNSServerIPAddr2 OBJECT-TYPE
--		SYNTAX    IpAddress
--		ACCESS    read-write
--		STATUS    mandatory
--		DESCRIPTION
--			"2th dns server ip address."
--		::= { swhNetworkConfiguration 14 }

--	swhNetDNSServerIPAddr3 OBJECT-TYPE
--		SYNTAX    IpAddress
--		ACCESS    read-write
--		STATUS    mandatory
--		DESCRIPTION
--			"3rd dns server ip address."
--		::= { swhNetworkConfiguration 48 }

	swhNetIPSourceBinding OBJECT-TYPE
		SYNTAX    INTEGER { disable(0), enable(1) }
		ACCESS    read-write
		STATUS    mandatory
		DESCRIPTION
			"Security IP enable or disable"
		::= { swhNetworkConfiguration 20 }


-- NetworkManagement(3).NetworkConfiguration(1).IPSourceBindingTable(21)

	swhNetIPSourceBindingTable OBJECT-TYPE
		SYNTAX    SEQUENCE OF SwhNetIPSourceBindingEntry
		ACCESS    not-accessible
		STATUS    mandatory
		DESCRIPTION
			"Table of Security IP information."
		::= { swhNetworkConfiguration 21 }

	-- Table Entry
	swhNetIPSourceBindingEntry OBJECT-TYPE
		SYNTAX    SwhNetIPSourceBindingEntry
		ACCESS    not-accessible
		STATUS    mandatory
		DESCRIPTION
			"An entry in the table, containing information
			 about SNMP agent.
			 Only Administrator can read this table"
		INDEX    { swhNetIPSourceBindingIndex }
		::= { swhNetIPSourceBindingTable 1 }

	SwhNetIPSourceBindingEntry ::=
		SEQUENCE {
			swhNetIPSourceBindingIndex
				INTEGER,
			swhNetIPSourceBindingState
				INTEGER,
			swhNetIPSourceBindingIPAddress
				DisplayString,
			swhNetIPSourceBindingIPv6Address
				DisplayString,
			swhNetIPSourceBindingDelete
				INTEGER
		}

	swhNetIPSourceBindingIndex OBJECT-TYPE
		SYNTAX    INTEGER (0..2147483647)
		ACCESS    not-accessible
		STATUS    mandatory
		DESCRIPTION
			"Security IP index"
		::= { swhNetIPSourceBindingEntry 1 }

	swhNetIPSourceBindingState OBJECT-TYPE
		SYNTAX    INTEGER { disable(0), enable(1) }
		ACCESS    read-write
		STATUS    mandatory
		DESCRIPTION
			"Security IP State"
		::= { swhNetIPSourceBindingEntry 3 }

	swhNetIPSourceBindingIPAddress OBJECT-TYPE
		SYNTAX    DisplayString
		ACCESS    read-write
		STATUS    mandatory
		DESCRIPTION
			"Security IPv4 Address"
		::= { swhNetIPSourceBindingEntry 4 }

	swhNetIPSourceBindingIPv6Address OBJECT-TYPE
		SYNTAX    DisplayString
		ACCESS    read-write
		STATUS    mandatory
		DESCRIPTION
			"Security IPv6 Address"
		::= { swhNetIPSourceBindingEntry 5 }

	swhNetIPSourceBindingDelete OBJECT-TYPE
		SYNTAX    INTEGER { normal(0), delete(1) }
		ACCESS    read-write
		STATUS    mandatory
		DESCRIPTION
			"Delete this entry."
		::= { swhNetIPSourceBindingEntry 10 }


-- NetworkManagement(3).NetworkConfiguration(1).NetCurrentDNSServerIPorIPv6Addr(28)

--	swhNetCurrentDNSServerIPorIPv6AddrTable OBJECT-TYPE
--		SYNTAX    SEQUENCE OF SwhNetCurrentDNSServerIPorIPv6AddrEntry
--		ACCESS    not-accessible
--		STATUS    mandatory
--		DESCRIPTION
--			"Table of IPv6 current state."
--		::= { swhNetworkConfiguration 28 }

	-- Table Entry
--	swhNetCurrentDNSServerIPorIPv6AddrEntry OBJECT-TYPE
--		SYNTAX    SwhNetCurrentDNSServerIPorIPv6AddrEntry
--		ACCESS    not-accessible
--		STATUS    mandatory
--		DESCRIPTION
--			"An entry in the table, containing information
--			 about DNS server Current State."
--		INDEX     { swhNetCurrentDNSServerIPorIPv6AddrIndex }
--		::= { swhNetCurrentDNSServerIPorIPv6AddrTable 1 }

--	SwhNetCurrentDNSServerIPorIPv6AddrEntry ::=
--		SEQUENCE {
--			swhNetCurrentDNSServerIPorIPv6AddrIndex
--				INTEGER,
--			swhNetCurrentDNSServerIPorIPv6AddrState
--				DisplayString
--		}

--	swhNetCurrentDNSServerIPorIPv6AddrIndex OBJECT-TYPE
--		SYNTAX    INTEGER (0..2147483647)
--		ACCESS    not-accessible
--		STATUS    mandatory
--		DESCRIPTION
--			"A unique value for each port."
--		::= { swhNetCurrentDNSServerIPorIPv6AddrEntry 1 }

--	swhNetCurrentDNSServerIPorIPv6AddrState OBJECT-TYPE
--		SYNTAX    DisplayString
--		ACCESS    read-only
--		STATUS    mandatory
--		DESCRIPTION
--			"Table of DNS server addr current state."
--		::= { swhNetCurrentDNSServerIPorIPv6AddrEntry 2 }


-- NetworkManagement(3).NetworkConfiguration(1).NetIPv6(32)

	swhNetIPv6En OBJECT-TYPE
		SYNTAX    INTEGER { enable(1), disable(0) }
		ACCESS    read-write
		STATUS    mandatory
		DESCRIPTION
			"enable/disable IPv6 address."
		::= { swhNetworkConfiguration 32 }

	swhNetIPv6AutoConfig OBJECT-TYPE
		SYNTAX    INTEGER { enable(1), disable(0) }
		ACCESS    read-write
		STATUS    mandatory
		DESCRIPTION
			"Configuration of IPv6 addresses using stateless autoconfig."
		::= { swhNetworkConfiguration 33 }

	swhNetIPv6LinkLocalAddr OBJECT-TYPE
		SYNTAX    DisplayString (SIZE (0..255))
		ACCESS    read-write
		STATUS    mandatory
		DESCRIPTION
			"The IPv6 link-local address to which this entry's addressing
			 information pertains."
		::= { swhNetworkConfiguration 34 }

	swhNetIPv6GlobalAddr OBJECT-TYPE
		SYNTAX    DisplayString (SIZE (0..255))
		ACCESS    read-write
		STATUS    mandatory
		DESCRIPTION
			"The IPv6 address to which this entry's addressing
			 information pertains."
		::= { swhNetworkConfiguration 35 }

	swhNetIPv6Gateway OBJECT-TYPE
		SYNTAX    DisplayString (SIZE (0..255))
		ACCESS    read-write
		STATUS    mandatory
		DESCRIPTION
			"IPv6 Gateway."
		::= { swhNetworkConfiguration 36 }

	swhNetDHCPv6 OBJECT-TYPE
		SYNTAX    INTEGER { force(2), auto(1), disable(0) }
		ACCESS    read-write
		STATUS    mandatory
		DESCRIPTION
			"auto will get IPv6 from DHCPv6."
		::= { swhNetworkConfiguration 37 }

	swhNetRapidCommit OBJECT-TYPE
		SYNTAX    INTEGER { enable(1), disable(0) }
		ACCESS    read-write
		STATUS    mandatory
		DESCRIPTION
			"set DHCPv6 rapid-commit"
		::= { swhNetworkConfiguration 38 }

	swhNetCurrentIPv6LinklocalAddr OBJECT-TYPE
		SYNTAX    DisplayString (SIZE (0..255))
		ACCESS    read-only
		STATUS    mandatory
		DESCRIPTION
			"Table of IPv6 current state."
		::= { swhNetworkConfiguration 39 }

	swhNetCurrentIPv6GatewayAddr OBJECT-TYPE
		SYNTAX    DisplayString (SIZE (0..255))
		ACCESS    read-only
		STATUS    mandatory
		DESCRIPTION
			"IPv6 config name"
		::= { swhNetworkConfiguration 40 }

	swhNetCurrentDHCPv6DUID OBJECT-TYPE
		SYNTAX    DisplayString (SIZE (0..255))
		ACCESS    read-only
		STATUS    mandatory
		DESCRIPTION
			"IPv6 config current state."
		::= { swhNetworkConfiguration 41 }

--	swhNetDNSServerIPv6Auto OBJECT-TYPE
--		SYNTAX    INTEGER { manually(0), automatically(1) }
--		ACCESS    read-write
--		STATUS    mandatory
--		DESCRIPTION
--			"dns server 0: DNS Manually 1: DNS Automatically."
--		::= { swhNetworkConfiguration 49 }

--	swhNetDNSServerIPv6Addr OBJECT-TYPE
--		SYNTAX    DisplayString (SIZE (0..255))
--		ACCESS    read-write
--		STATUS    mandatory
--		DESCRIPTION
--			"dns server IPv6 address."
--		::= { swhNetworkConfiguration 30 }

--	swhNetDNSServerIPv6Addr2 OBJECT-TYPE
--		SYNTAX    DisplayString (SIZE (0..255))
--		ACCESS    read-write
--		STATUS    mandatory
--		DESCRIPTION
--			"2th dns server IPv6 address."
--		::= { swhNetworkConfiguration 31 }

--	swhNetDNSServerIPv6Addr3 OBJECT-TYPE
--		SYNTAX    DisplayString (SIZE (0..255))
--		ACCESS    read-write
--		STATUS    mandatory
--		DESCRIPTION
--			"3rd dns server IPv6 address."
--		::= { swhNetworkConfiguration 50 }


-- NetworkManagement(3).NetworkConfiguration(1).NetCurrentIPv6GlobalAddrTable(45)

--	swhNetCurrentIPv6GlobalAddrTable OBJECT-TYPE
--		SYNTAX    SEQUENCE OF SwhNetCurrentIPv6GlobalAddrEntry
--		ACCESS    not-accessible
--		STATUS    mandatory
--		DESCRIPTION
--			"Table of IPv6 current state."
--		::= { swhNetworkConfiguration 45 }

	-- Table Entry
--	swhNetCurrentIPv6GlobalAddrEntry OBJECT-TYPE
--		SYNTAX    SwhNetCurrentIPv6GlobalAddrEntry
--		ACCESS    not-accessible
--		STATUS    mandatory
--		DESCRIPTION
--			"An entry in the table, containing information
--			 about IPv6 Current State."
--		INDEX     { swhNetCurrentIPv6GlobalAddrIndex }
--		::= { swhNetCurrentIPv6GlobalAddrTable 1 }

--	SwhNetCurrentIPv6GlobalAddrEntry ::=
--		SEQUENCE {
--			swhNetCurrentIPv6GlobalAddrIndex
--				INTEGER,
--			swhNetCurrentIPv6GlobalAddrState
--				DisplayString
--		}

--	swhNetCurrentIPv6GlobalAddrIndex OBJECT-TYPE
--		SYNTAX    INTEGER (0..2147483647)
--		ACCESS    not-accessible
--		STATUS    mandatory
--		DESCRIPTION
--			"A unique value for each port."
--		::= { swhNetCurrentIPv6GlobalAddrEntry 1 }

--	swhNetCurrentIPv6GlobalAddrState OBJECT-TYPE
--		SYNTAX    DisplayString
--		ACCESS    read-only
--		STATUS    mandatory
--		DESCRIPTION
--			"Table of IPv6 global addr current state."
--		::= { swhNetCurrentIPv6GlobalAddrEntry 2 }


-- NetworkManagement(3).SystemServiceConfiguration(2)

	swhServiceTelnetThreadEn OBJECT-TYPE
		SYNTAX    INTEGER { disable(0), enable(1) }
		ACCESS    read-write
		STATUS    mandatory
		DESCRIPTION
			"Enable Telnet Thread,
			 Only Administrator can write this page"
		::= { swhSystemServiceConfiguration 1 }

	swhServiceSSHThreadEn OBJECT-TYPE
		SYNTAX    INTEGER { disable(0), enable(1) }
		ACCESS    read-write
		STATUS    mandatory
		DESCRIPTION
			"Enable SSH Thread,
			 Only Administrator can write this page"
		::= { swhSystemServiceConfiguration 10 }

	swhServiceSNMPThreadEn OBJECT-TYPE
		SYNTAX    INTEGER { disable(0), enable(1) }
		ACCESS    read-write
		STATUS    mandatory
		DESCRIPTION
			"Enable SNMP Thread
			 Only Administrator can write this page"
		::= { swhSystemServiceConfiguration 3 }

	swhServiceWebThreadEn OBJECT-TYPE
		SYNTAX    INTEGER { disable(0), http(1), https(2) }
		ACCESS    read-write
		STATUS    mandatory
		DESCRIPTION
			"Enable Web Thread
			 Only Administrator can write this page"
		::= { swhSystemServiceConfiguration 4 }

--	swhServiceConsolePortThreadEn OBJECT-TYPE
--		SYNTAX    INTEGER { disable(0), enable(1) }
--		ACCESS    read-write
--		STATUS    mandatory
--		DESCRIPTION
--			"Enable Console Port Thread,
--			 Only Administrator can write this page"
--		::= { swhSystemServiceConfiguration 12 }


-- NetworkManagement(3).RS232TelnetConsoleConfiguration(3)

--	swhRS232BaudRate OBJECT-TYPE
--		SYNTAX    INTEGER
--		ACCESS    read-only
--		STATUS    mandatory
--		DESCRIPTION
--			"RS232 Baud Rate  (bps)
--			9600 14400 19200 38400 57600 115200 are avaivable value
--			Only Administrator can write this page"
--		::= { swhRS232TelnetConsoleConfiguration 2 }
--
--	swhRS232StopBits OBJECT-TYPE
	--	SYNTAX    INTEGER { "1"(1), "1.5"(2), "2"(3) }
--		SYNTAX    INTEGER { x1(1), x1-5(2), x2(3) }
--		ACCESS    read-only
--		STATUS    mandatory
--		DESCRIPTION
--			"RS232 Stop Bits
--			Only Administrator can write this page"
--		::= { swhRS232TelnetConsoleConfiguration 3 }
--
--	swhRS232ParityCheck OBJECT-TYPE
--		SYNTAX    INTEGER { none(0), even(1), odd(2), mark(3), space(4) }
--		ACCESS    read-only
--		STATUS    mandatory
--		DESCRIPTION
--			"RS232 Parity Check
--			Only Administrator can write this page"
--		::= { swhRS232TelnetConsoleConfiguration 4 }
--
--	swhRS232WordLength OBJECT-TYPE
--		SYNTAX    INTEGER
--		ACCESS    read-only
--		STATUS    mandatory
--		DESCRIPTION
--			"RS232 Word Length
--			5 6 7 8 are available value
--			Only Administrator can write this page"
--		::= { swhRS232TelnetConsoleConfiguration 5 }
--
--	swhRS232FlowControl OBJECT-TYPE
--		SYNTAX    INTEGER { none(0), hardware(1) }
--		ACCESS    read-only
--		STATUS    mandatory
--		DESCRIPTION
--			"RS232 Flow Control
--			Only Administrator can write this page"
--		::= { swhRS232TelnetConsoleConfiguration 6 }

	swhTelnetPort OBJECT-TYPE
		SYNTAX    INTEGER 
		ACCESS    read-write
		STATUS    mandatory
		DESCRIPTION
			"telnet port 1-65534
			Only Administrator can write this page"
		::= { swhRS232TelnetConsoleConfiguration 8 }

	swhCLITimeOutTime OBJECT-TYPE
		SYNTAX    INTEGER (1..1440)
		ACCESS    read-write
		STATUS    mandatory
		DESCRIPTION
			"Time out time.
			1-1440 are valid value.
			Only Administrator can write this page"
		::= { swhRS232TelnetConsoleConfiguration 11 }

	swhCLITimeOutTimeUnit OBJECT-TYPE
		SYNTAX    INTEGER { seconds(0), minutes(1) }
		ACCESS    read-write
		STATUS    mandatory
		DESCRIPTION
			"System Time Out Unit.
			(0 : seconds, 1 : minutes)"
		::= { swhRS232TelnetConsoleConfiguration 12 }

	swhWebTimeOutTime OBJECT-TYPE
		SYNTAX    INTEGER (1..1440)
		ACCESS    read-write
		STATUS    mandatory
		DESCRIPTION
			"Web Time out time.
			1-1440 are valid value."
		::= { swhRS232TelnetConsoleConfiguration 13 }

--	swhConsolePortFailRetry OBJECT-TYPE
--		SYNTAX    INTEGER (1..10)
--		ACCESS    read-write
--		STATUS    mandatory
--		DESCRIPTION
--			"Console port fail retry
--			1-10 are valid value"
--		::= { swhRS232TelnetConsoleConfiguration 14 }
--
--	swhConsolePortFailBlockTime OBJECT-TYPE
--		SYNTAX    INTEGER (1..60)
--		ACCESS    read-write
--		STATUS    mandatory
--		DESCRIPTION
--			"Console port fail Block Time
--			1-120 are valid value"
--		::= { swhRS232TelnetConsoleConfiguration 15 }


-- NetworkManagement(3).DeviceCommunity(4)

	swhAgentTable OBJECT-TYPE
		SYNTAX    SEQUENCE OF SwhAgentEntry
		ACCESS    not-accessible
		STATUS    mandatory
		DESCRIPTION
			"Table of Agent information."
		::= { swhDeviceCommunity 1 }

	-- Table Entry
	swhAgentEntry OBJECT-TYPE
		SYNTAX    SwhAgentEntry
		ACCESS    not-accessible
		STATUS    mandatory
		DESCRIPTION
			"An entry in the table, containing information
			 about SNMP agent.
			 Only Administrator can read this table"
		INDEX    { swhAgentIndex }
		::= { swhAgentTable 1 }

	SwhAgentEntry ::=
		SEQUENCE {
			swhAgentIndex
				INTEGER,
			swhAgentValid
				INTEGER,
			swhAgentEnable
				INTEGER,
			swhAgentCommunity
				DisplayString,
		--	swhAgentPassword
		--		DisplayString,
			swhAgentDescription
				DisplayString,
		--	swhAgentIPSecurity
		--		INTEGER,
		--	swhAgentIPAddr
		--		IpAddress,
			swhAgentSNMPLevel
				INTEGER,
			swhAgentDelete
				INTEGER
		}

	swhAgentIndex OBJECT-TYPE
		SYNTAX    INTEGER (0..2147483647)
		ACCESS    not-accessible
		STATUS    mandatory
		DESCRIPTION
			"Agent index"
		::= { swhAgentEntry 1 }

	swhAgentValid OBJECT-TYPE
		SYNTAX    INTEGER { invalid(0), valid(1) }
		ACCESS    read-only
		STATUS    mandatory
		DESCRIPTION
			"Valid"
		::= { swhAgentEntry 2 }

	swhAgentEnable OBJECT-TYPE
		SYNTAX    INTEGER { disable(0), enable(1) }
		ACCESS    read-write
		STATUS    mandatory
		DESCRIPTION
			"Enable"
		::= { swhAgentEntry 3 }

	swhAgentCommunity OBJECT-TYPE
		SYNTAX    DisplayString (SIZE (0..255))
		ACCESS    read-write
		STATUS    mandatory
		DESCRIPTION
			"SNMP community Name"
		::= { swhAgentEntry 4 }

	--swhAgentPassword OBJECT-TYPE
	--	SYNTAX    DisplayString (SIZE (0..255))
	--	ACCESS    read-write
	--	STATUS    mandatory
	--	DESCRIPTION
	--		"Password, this field not used, reserve"
	--	::= { swhAgentEntry 5 }

	swhAgentDescription OBJECT-TYPE
		SYNTAX    DisplayString (SIZE (0..255))
		ACCESS    read-write
		STATUS    mandatory
		DESCRIPTION
			"Description"
		::= { swhAgentEntry 6 }

	--swhAgentIPSecurity OBJECT-TYPE
	--	SYNTAX    INTEGER { disable(0), enable(1) }
	--	ACCESS    read-write
	--	STATUS    mandatory
	--	DESCRIPTION
	--		"IP Security, if enable, 
	--		 only swhAgentIPAddr could walk or set SNMP"
	--	::= { swhAgentEntry 7 }

	--swhAgentIPAddr OBJECT-TYPE
	--	SYNTAX    IpAddress
	--	ACCESS    read-write
	--	STATUS    mandatory
	--	DESCRIPTION
	--		"The IP address from which could walk or set SNMP."
	--	::= { swhAgentEntry 8 }

	swhAgentSNMPLevel OBJECT-TYPE
		SYNTAX    INTEGER { readonly(1), readwrite(2), administrator(3) }
		ACCESS    read-write
		STATUS    mandatory
		DESCRIPTION
			"SNMP Level"
		::= { swhAgentEntry 9 }

	swhAgentDelete OBJECT-TYPE
		SYNTAX    INTEGER { normal(0), delete(1) }
		ACCESS    read-write
		STATUS    mandatory
		DESCRIPTION
			"Delete this entry."
		::= { swhAgentEntry 10 }

	swhSNMPv3AgentTable OBJECT-TYPE
		SYNTAX    SEQUENCE OF SwhSNMPv3AgentEntry
		ACCESS    not-accessible
		STATUS    mandatory
		DESCRIPTION
			"Table of Agent information."
		::= { swhDeviceCommunity 5 }

	-- Table Entry
	swhSNMPv3AgentEntry OBJECT-TYPE
		SYNTAX    SwhSNMPv3AgentEntry
		ACCESS    not-accessible
		STATUS    mandatory
		DESCRIPTION
			"An entry in the table, containing information
			 about SNMP agent.
			 Only Administrator can read this table"
		INDEX    { swhSNMPv3AgentIndex }
		::= { swhSNMPv3AgentTable 1 }

	swhSNMPv3Encryption OBJECT-TYPE
		SYNTAX    INTEGER { disable(0), aes-128(1) }
		ACCESS    read-write
		STATUS    mandatory
		DESCRIPTION
			"Enable or disable SNMPv3 Encryption."
		::= { swhSNMPv3AgentTable 2 }

	SwhSNMPv3AgentEntry ::=
		SEQUENCE {
			swhSNMPv3AgentIndex
				INTEGER,
			swhSNMPv3AgentValid
				INTEGER,
		--	swhSNMPv3AgentEnable
		--		INTEGER,
			swhSNMPv3AgentUserName
				DisplayString,
			swhSNMPv3AgentAuthentication
				INTEGER,
			swhSNMPv3AgentAuthPassword
				DisplayString,
			swhSNMPv3AgentPrivate
				INTEGER,
			swhSNMPv3AgentPrivPassword
				DisplayString
		--	swhSNMPv3AgentSNMPLevel
		--		INTEGER
		--	swhAgentDelete
		--		INTEGER
		}

	swhSNMPv3AgentIndex OBJECT-TYPE
		SYNTAX    INTEGER (0..2147483647)
		ACCESS    not-accessible
		STATUS    mandatory
		DESCRIPTION
			"Agent index"
		::= { swhSNMPv3AgentEntry 1 }

	swhSNMPv3AgentValid OBJECT-TYPE
		SYNTAX    INTEGER { invalid(0), valid(1) }
		ACCESS    read-only
		STATUS    mandatory
		DESCRIPTION
			"Valid"
		::= { swhSNMPv3AgentEntry 3 }

--	swhSNMPv3AgentEnable OBJECT-TYPE
--		SYNTAX    INTEGER { disable(0), enable(1) }
--		ACCESS    read-only
--		STATUS    mandatory
--		DESCRIPTION
--			"Enable"
--		::= { swhSNMPv3AgentEntry 5 }

	swhSNMPv3AgentUserName OBJECT-TYPE
		SYNTAX    DisplayString (SIZE (0..255))
		ACCESS    read-only
		STATUS    mandatory
		DESCRIPTION
			"SNMPv3 UserName"
		::= { swhSNMPv3AgentEntry 7 }
		
	swhSNMPv3AgentAuthentication OBJECT-TYPE
		SYNTAX    INTEGER { none(0), md5(1), sha(2) }
		ACCESS    read-write
		STATUS    mandatory
		DESCRIPTION
			"Authentication"
		::= { swhSNMPv3AgentEntry 9 }

	swhSNMPv3AgentAuthPassword OBJECT-TYPE
		SYNTAX    DisplayString (SIZE (0..255))
		ACCESS    read-write
		STATUS    mandatory
		DESCRIPTION
			"Authentication Password"
		::= { swhSNMPv3AgentEntry 11 }

	swhSNMPv3AgentPrivate OBJECT-TYPE
		SYNTAX    INTEGER { none(0), des(1), aes-128(2) }
		ACCESS    read-write
		STATUS    mandatory
		DESCRIPTION
			"Authentication"
		::= { swhSNMPv3AgentEntry 12 }

	swhSNMPv3AgentPrivPassword OBJECT-TYPE
		SYNTAX    DisplayString (SIZE (0..255))
		ACCESS    read-write
		STATUS    mandatory
		DESCRIPTION
			"Authentication Password"
		::= { swhSNMPv3AgentEntry 13 }

--	swhSNMPv3AgentSNMPLevel OBJECT-TYPE
--		SYNTAX    INTEGER { None(0), readonly(1), readwrite(2), administrator(3) }
--		ACCESS    read-only
--		STATUS    mandatory
--		DESCRIPTION
--			"SNMPv3 Level"
--		::= { swhSNMPv3AgentEntry 17 }

	SwhSNMPv3AuthEntry ::=
		SEQUENCE {
			swhSNMPv3AgentIndex
				INTEGER,
			swhSNMPv3AgentValid
				INTEGER,
			swhSNMPv3AgentUserName
				DisplayString,
			swhSNMPv3AgentAuthentication
				INTEGER,
			swhSNMPv3AgentAuthPassword
				DisplayString
		}
		
	SwhSNMPv3PrivEntry ::=
		SEQUENCE {
			swhSNMPv3AgentIndex
				INTEGER,
			swhSNMPv3AgentValid
				INTEGER,
			swhSNMPv3AgentUserName
				DisplayString,
			swhSNMPv3AgentPrivate
				INTEGER,
			swhSNMPv3AgentPrivPassword
				DisplayString
		}


-- NetworkManagement(3).TrapDestination(5)

	swhTrapDestTable OBJECT-TYPE
		SYNTAX    SEQUENCE OF SwhTrapDestEntry
		ACCESS    not-accessible
		STATUS    mandatory
		DESCRIPTION
			"Table of Trap destination."
		::= { swhTrapDestination 1 }

	-- Table Entry
	swhTrapDestEntry OBJECT-TYPE
		SYNTAX    SwhTrapDestEntry
		ACCESS    not-accessible
		STATUS    mandatory
		DESCRIPTION
			"An entry in the table, containing information
			 about SNMP Trap Destination.
			 Only Administrator can read this table"
		INDEX    { swhTrapDestIndex }
		::= { swhTrapDestTable 1 }

	SwhTrapDestEntry ::=
		SEQUENCE {
			swhTrapDestIndex
				INTEGER,
		--	swhTrapDestValid
		--		INTEGER,
			swhTrapDestEnable
				INTEGER,
			swhTrapDestIPAddr
				IpAddress,
			swhTrapDestIPv6Addr
				DisplayString,
		--	swhTrapDestServer
		--		DisplayString,
			swhTrapDestCommunity
				DisplayString
		}

	swhTrapDestIndex OBJECT-TYPE
		SYNTAX    INTEGER (0..2147483647)
		ACCESS    not-accessible
		STATUS    mandatory
		DESCRIPTION
			"Trap Destination index"
		::= { swhTrapDestEntry 1 }

	--swhTrapDestValid OBJECT-TYPE
	--	SYNTAX    INTEGER { valid(1), invalid(0) }
	--	ACCESS    read-only
	--	STATUS    mandatory
	--	DESCRIPTION
	--		"Valid"
	--	::= { swhTrapDestEntry 2 }

	swhTrapDestEnable OBJECT-TYPE
		SYNTAX    INTEGER { disable(0), enable(1) }
		ACCESS    read-write
		STATUS    mandatory
		DESCRIPTION
			"Enable"
		::= { swhTrapDestEntry 3 }

	swhTrapDestCommunity OBJECT-TYPE
		SYNTAX    DisplayString (SIZE (0..255))
		ACCESS    read-write
		STATUS    mandatory
		DESCRIPTION
			"SNMP community Name"
		::= { swhTrapDestEntry 4 }

	swhTrapDestIPAddr OBJECT-TYPE
		SYNTAX    IpAddress
		ACCESS    read-write
		STATUS    mandatory
		DESCRIPTION
			"The IP address SNMP TRAP send to"
		::= { swhTrapDestEntry 8 }

	swhTrapDestIPv6Addr OBJECT-TYPE
		SYNTAX    DisplayString (SIZE (0..255))
		ACCESS    read-write
		STATUS    mandatory
		DESCRIPTION
			"The IPv6 address SNMP TRAP send to"
		::= { swhTrapDestEntry 9 }

--	swhTrapDestServer OBJECT-TYPE
--		SYNTAX    DisplayString (SIZE (0..255))
--		ACCESS    read-write
--		STATUS    mandatory
--		DESCRIPTION
--			"The domain name SNMP TRAP send to"
--		::= { swhTrapDestEntry 10 }


-- NetworkManagement(3).TrapConfiguration(6)

	swhTrapColdStart OBJECT-TYPE
		SYNTAX    INTEGER { disable(0), enable(1) }
		ACCESS    read-write
		STATUS    mandatory
		DESCRIPTION
			"cold start trap enable or disable"
		::= { swhTrapConfiguration 1 }

	swhTrapWarmStart OBJECT-TYPE
		SYNTAX    INTEGER { disable(0), enable(1) }
		ACCESS    read-write
		STATUS    mandatory
		DESCRIPTION
			"warm start trap enable or disable"
		::= { swhTrapConfiguration 2 }

	swhTrapAuthenticationFailure OBJECT-TYPE
		SYNTAX    INTEGER { disable(0), enable(1) }
		ACCESS    read-write
		STATUS    mandatory
		DESCRIPTION
			"authentication failure trap enable or disable"
		::= { swhTrapConfiguration 3 }

	swhTrapPortLink OBJECT-TYPE
		SYNTAX    INTEGER { disable(0), enable(1) }
		ACCESS    read-write
		STATUS    mandatory
		DESCRIPTION
			"port link up/down trap enable or disable"
		::= { swhTrapConfiguration 4 }

	swhTrapPortLinkFlap OBJECT-TYPE
		SYNTAX    INTEGER { disable(0), enable(1) }
		ACCESS    read-write
		STATUS    mandatory
		DESCRIPTION
			"Port link flap trap enable or disable"
		::= { swhTrapConfiguration 19 }

--	swhTrapCaseFan OBJECT-TYPE
--		SYNTAX    INTEGER { disable(0), enable(1) }
--		ACCESS    read-write
--		STATUS    mandatory
--		DESCRIPTION
--			"local machine case fan trap enable or disable"
--		::= { swhTrapConfiguration 9 }

	swhTrapSystemPowerDown OBJECT-TYPE
		SYNTAX    INTEGER { disable(0), enable(1) }
		ACCESS    read-write
		STATUS    mandatory
		DESCRIPTION
			"local machine system power down trap enable or disable"
		::= { swhTrapConfiguration 5 }

	swhTrapCPULoading OBJECT-TYPE
		SYNTAX    INTEGER { disable(0), enable(1) }
		ACCESS    read-write
		STATUS    mandatory
		DESCRIPTION
			"CPU Loading trap enable or disable"
		::= { swhTrapConfiguration 11 }

--	swhTrapDigitalState OBJECT-TYPE
--		SYNTAX    INTEGER { disable(0), enable(1) }
--		ACCESS    read-write
--		STATUS    mandatory
--		DESCRIPTION
--			"digital I/O trap enable or disable"
--		::= { swhTrapConfiguration 16 }

	swhTrapAutoBackup OBJECT-TYPE
		SYNTAX    INTEGER { disable(0), enable(1) }
		ACCESS    read-write
		STATUS    mandatory
		DESCRIPTION
			"auto-backup trap enable or disable"
		::= { swhTrapConfiguration 13 }

	swhTrapStormControl OBJECT-TYPE
		SYNTAX    INTEGER { disable(0), enable(1) }
		ACCESS    read-write
		STATUS    mandatory
		DESCRIPTION
			"Storm control threshold is exceeded trap enable or disable"
		::= { swhTrapConfiguration 15 }

--	swhTrapMACLimiter OBJECT-TYPE
--		SYNTAX    INTEGER { disable(0), enable(1) }
--		ACCESS    read-write
--		STATUS    mandatory
--		DESCRIPTION
--			"MAC table threshold is exceeded trap enable or disable"
--		::= { swhTrapConfiguration 14 }

--	swhTrapConsolePortLink OBJECT-TYPE
--		SYNTAX    INTEGER { disable(0), enable(1) }
--		ACCESS    read-write
--		STATUS    mandatory
--		DESCRIPTION
--			"Console port link up/down trap enable or disable"
--		::= { swhTrapConfiguration 17 }

	swhTrapCPUTemperature OBJECT-TYPE
		SYNTAX    INTEGER { disable(0), enable(1) }
		ACCESS    read-write
		STATUS    mandatory
		DESCRIPTION
			"CPU temperature trap enable or disable"
		::= { swhTrapConfiguration 18 }

--	swhTrapFastRedundancy OBJECT-TYPE
--		SYNTAX    INTEGER { disable(0), enable(1) }
--		ACCESS    read-write
--		STATUS    mandatory
--		DESCRIPTION
--			"Fast Redundancy port link up/down trap enable or disable"
--		::= { swhTrapConfiguration 75 }

--	swhTrapPoEBudget OBJECT-TYPE
--		SYNTAX    INTEGER { disable(0), enable(1) }
--		ACCESS    read-write
--		STATUS    mandatory
--		DESCRIPTION
--			"PoEBudget trap enable or disable"
--		::= { swhTrapConfiguration 76 }

--	swhTrapSystemVoltage OBJECT-TYPE
--		SYNTAX    INTEGER { disable(0), enable(1) }
--		ACCESS    read-write
--		STATUS    mandatory
--		DESCRIPTION
--			"System Voltage trap enable or disable"
--		::= { swhTrapConfiguration 77 }


-- NetworkManagement(3).TimeServerConfiguration(7)

	swhTimeSync OBJECT-TYPE
		SYNTAX    INTEGER { disable(0), enable(1) }
		ACCESS    read-write
		STATUS    mandatory
		DESCRIPTION
			"Time Synchronization"
		::= { swhTimeServerConfiguration 1 }

	swhTimeServerIPAddr OBJECT-TYPE
		SYNTAX    IpAddress
		ACCESS    read-write
		STATUS    mandatory
		DESCRIPTION
			"time server ip address."
		::= { swhTimeServerConfiguration 2 }

	swhTimeServerIPAddr2 OBJECT-TYPE
		SYNTAX    IpAddress
		ACCESS    read-write
		STATUS    mandatory
		DESCRIPTION
			"2th time server ip address."
		::= { swhTimeServerConfiguration 3 }

--	swhTimeServerConfig OBJECT-TYPE
--		SYNTAX    DisplayString
--		ACCESS    read-write
--		STATUS    mandatory
--		DESCRIPTION
--			"time server Server Config."
--		::= { swhTimeServerConfiguration 22 }

--	swhTimeServerConfig2 OBJECT-TYPE
--		SYNTAX    DisplayString
--		ACCESS    read-write
--		STATUS    mandatory
--		DESCRIPTION
--			"2th time server Server Config."
--		::= { swhTimeServerConfiguration 23 }

	swhTimeSyncInterval OBJECT-TYPE
		SYNTAX    INTEGER { hour1(1),
		                    hour2(2),
		                    hour3(3),
		                    hour4(4),
		                    hour6(5),
		                    hour8(6),
		                    hour12(7),
		                    hour24(8)
		                  }
		ACCESS    read-write
		STATUS    mandatory
		DESCRIPTION
			"Time Synchronization Interval, unit is min."
		::= { swhTimeServerConfiguration 4 }

	swhTimeZoneIndex OBJECT-TYPE
		SYNTAX    INTEGER
		ACCESS    read-write
		STATUS    mandatory
		DESCRIPTION
			"time zone
			 0:   GMT-11:00  Apia
			 1:   GMT-10:00  Honolulu
			 2:   GMT-9:00  Anchorage
			 3:   GMT-8:00  Vancouver
			 4:   GMT-8:00  San Francisco
			 5:   GMT-8:00  Seattle
			 6:   GMT-8:00  Los Angeles
			 7:   GMT-7:00  Phoenix
			 8:   GMT-7:00  Aklavik
			 9:   GMT-7:00  Edmonton
			10:   GMT-7:00  Denver
			11:   GMT-6:00  Guatemala
			12:   GMT-6:00  San Salvador
			13:   GMT-6:00  Tegucigalpa
			14:   GMT-6:00  Managua
			15:   GMT-6:00  Mexico City
			16:   GMT-6:00  Winnipeg
			17:   GMT-6:00  Houston
			18:   GMT-6:00  Minneapolis
			19:   GMT-6:00  St. Paul
			20:   GMT-6:00  New Orleans
			21:   GMT-6:00  Chicago
			22:   GMT-6:00  Montgomery
			23:   GMT-5:00  Indianapolis
			24:   GMT-5:00  Lima
			25:   GMT-5:00  Kingston
			26:   GMT-5:00  Bogota
			27:   GMT-5:00  Atlanta
			28:   GMT-5:00  Detroit
			29:   GMT-5:00  Havana
			30:   GMT-5:00  Toronto
			31:   GMT-5:00  Nassau
			32:   GMT-5:00  Washington DC
			33:   GMT-5:00  Ottawa
			34:   GMT-5:00  Philadelphia
			35:   GMT-5:00  New York
			36:   GMT-5:00  Montreal
			37:   GMT-5:00  Boston
			38:   GMT-4:00  Santo Domingo
			39:   GMT-4:00  La Paz
			40:   GMT-4:00  Caracas
			41:   GMT-4:00  San Juan
			42:   GMT-4:00  Santiago
			43:   GMT-4:00  Halifax
			44:   GMT-4:00  Asuncion
			45:   GMT-3:00  Buenos Aires
			46:   GMT-3:00  Montevideo
			47:   GMT-3:00  Brasilia
			48:   GMT-3:00  Sao Paulo
			49:   GMT-3:00  Rio de Janeiro
			50:   GMT-2:00  Fernando de Noronha
			51:   GMT-1:00  Praia
			52:   GMT       Reykjavik
			53:   GMT       Casablanca
			54:   GMT       Lisbon
			55:   GMT       Dublin
			56:   GMT       London
			57:   GMT+1:00  Lagos
			58:   GMT+1:00  Algiers
			59:   GMT+1:00  Madrid
			60:   GMT+1:00  Barcelona
			61:   GMT+1:00  Paris
			62:   GMT+1:00  Brussels
			63:   GMT+1:00  Amsterdam
			64:   GMT+1:00  Geneva
			65:   GMT+1:00  Zurich
			66:   GMT+1:00  Frankfurt
			67:   GMT+1:00  Oslo
			68:   GMT+1:00  Copenhagen
			69:   GMT+1:00  Rome
			70:   GMT+1:00  Berlin
			71:   GMT+1:00  Prague
			72:   GMT+1:00  Zagreb
			73:   GMT+1:00  Vienna
			74:   GMT+1:00  Stockholm
			75:   GMT+1:00  Cape Town
			76:   GMT+1:00  Budapest
			77:   GMT+1:00  Belgrade
			78:   GMT+1:00  Warsaw
			79:   GMT+2:00  Johannesburg
			80:   GMT+2:00  Harare
			81:   GMT+2:00  Cairo
			82:   GMT+2:00  Jerusalem
			83:   GMT+2:00  Sofia
			84:   GMT+2:00  Athens
			85:   GMT+2:00  Tallinn
			86:   GMT+2:00  Helsinki
			87:   GMT+2:00  Bucharest
			88:   GMT+2:00  Minsk
			89:   GMT+2:00  Istanbul
			90:   GMT+2:00  Kyiv
			91:   GMT+2:00  Odesa
			92:   GMT+2:00  Khartoum
			93:   GMT+2:00  Ankara
			94:   GMT+2:00  Beirut
			95:   GMT+2:00  Amman
			96:   GMT+3:00  Nairobi
			97:   GMT+3:00  Addis Ababa
			98:   GMT+3:00  Baghdad
			99:   GMT+3:00  Aden
			100:  GMT+3:00  Riyadh
			101:  GMT+3:00  Antananarivo
			102:  GMT+3:00  Kuwait City
			103:  GMT+3:00  Moscow
			104:  GMT+4:00  Abu Dhabi
			105:  GMT+5:00  Karachi
			106:  GMT+5:00  Tashkent
			107:  GMT+5:00  Islamabad
			108:  GMT+5:00  Lahore
			109:  GMT+5:30  Mumbai
			110:  GMT+5:30  New Delhi
			111:  GMT+5:30  Kolkata
			112:  GMT+6:00  Dhaka
			113:  GMT+7:00  Bangkok
			114:  GMT+7:00  Hanoi
			115:  GMT+7:00  Jakarta
			116:  GMT+8:00  Kuala Lumpur
			117:  GMT+8:00  Singapore
			118:  GMT+8:00  Hong Kong
			119:  GMT+8:00  Perth
			120:  GMT+8:00  Beijing
			121:  GMT+8:00  Manila
			122:  GMT+8:00  Shanghai
			123:  GMT+8:00  Taipei
			124:  GMT+9:00  Seoul
			125:  GMT+9:00  Tokyo
			126:  GMT+10:00  Melbourne
			127:  GMT+10:00  Canberra
			128:  GMT+10:00  Sydney
			129:  GMT+10:00  Brisbane
			130:  GMT+10:00  Vladivostok
			131:  GMT+11:00  Kolonia
			132:  GMT+12:00  Suva
			133:  GMT+12:00  Kamchatka
			134:  GMT+12:00  Wellington
			135:  GMT+12:00  Anadyr
			"
		::= { swhTimeServerConfiguration 5 }

	swhTimeZone OBJECT-TYPE
		SYNTAX    DisplayString
		ACCESS    read-only
		STATUS    mandatory
		DESCRIPTION
			"TimeZone."
		::= { swhTimeServerConfiguration 6 }

	swhTimeDST OBJECT-TYPE
		SYNTAX    INTEGER { disable(0), recurring(1), date(2)}
		ACCESS    read-write
		STATUS    mandatory
		DESCRIPTION
			"disable or enable Daylight Saving Time."
		::= { swhTimeServerConfiguration 7 }

	swhTimeDSTRange OBJECT-TYPE
		SYNTAX    DisplayString
		ACCESS    read-write
		STATUS    mandatory
		DESCRIPTION
			"time range when Daylight Saving Time (swhTimeDST) is enable"
		::= { swhTimeServerConfiguration 9 }

	swhTimeServerIPv6Addr OBJECT-TYPE
		SYNTAX    DisplayString
		ACCESS    read-write
		STATUS    mandatory
		DESCRIPTION
			"time server IPv6 address."
		::= { swhTimeServerConfiguration 20 }

	swhTimeServerIPv6Addr2 OBJECT-TYPE
		SYNTAX    DisplayString
		ACCESS    read-write
		STATUS    mandatory
		DESCRIPTION
			"2th time server IPv6 address."
		::= { swhTimeServerConfiguration 21 }


-- NetworkManagement(3).MalAttemptLogConfiguration(8)

	swhLogServer OBJECT-TYPE
		SYNTAX    INTEGER { disable(0), enable(1) }
		ACCESS    read-write
		STATUS    mandatory
		DESCRIPTION
			"Log Server"
		::= { swhSyslogConfiguration 1 }

	swhLogSNTPStatus OBJECT-TYPE
		SYNTAX    INTEGER { disable(0), enable(1) }
		ACCESS    read-only
		STATUS    mandatory
		DESCRIPTION
			"SNTP Status"
		::= { swhSyslogConfiguration 3 }

	swhLogFacility OBJECT-TYPE
		SYNTAX    INTEGER { local-0(0),
		                    local-1(1),
		                    local-2(2),
		                    local-3(3),
		                    local-4(4),
		                    local-5(5),
		                    local-6(6),
		                    local-7(7)
		                  }
		ACCESS    read-write
		STATUS    mandatory
		DESCRIPTION
			"Log Facility Local 0-7"
		::= { swhSyslogConfiguration 12 }

	swhLogServerIPAddr1 OBJECT-TYPE
		SYNTAX    IpAddress
		ACCESS    read-write
		STATUS    mandatory
		DESCRIPTION
			"log server ip address 1."
		::= { swhSyslogConfiguration 4 }

	swhLogServerIPAddr2 OBJECT-TYPE
		SYNTAX    IpAddress
		ACCESS    read-write
		STATUS    mandatory
		DESCRIPTION
			"log server ip address 2."
		::= { swhSyslogConfiguration 5 }

	swhLogServerIPAddr3 OBJECT-TYPE
		SYNTAX    IpAddress
		ACCESS    read-write
		STATUS    mandatory
		DESCRIPTION
			"log server ip address 3."
		::= { swhSyslogConfiguration 6 }

	swhLogServerIPv6Addr1 OBJECT-TYPE
		SYNTAX    DisplayString (SIZE (0..255))
		ACCESS    read-write
		STATUS    mandatory
		DESCRIPTION
			"log server IPv6 address 1."
		::= { swhSyslogConfiguration 8 }

	swhLogServerIPv6Addr2 OBJECT-TYPE
		SYNTAX    DisplayString (SIZE (0..255))
		ACCESS    read-write
		STATUS    mandatory
		DESCRIPTION
			"log server IPv6 address 2."
		::= { swhSyslogConfiguration 9 }

	swhLogServerIPv6Addr3 OBJECT-TYPE
		SYNTAX    DisplayString (SIZE (0..255))
		ACCESS    read-write
		STATUS    mandatory
		DESCRIPTION
			"log server IPv6 address 3."
		::= { swhSyslogConfiguration 10 }

--	swhLogServer1 OBJECT-TYPE
--		SYNTAX    DisplayString (SIZE (0..255))
--		ACCESS    read-write
--		STATUS    mandatory
--		DESCRIPTION
--			"log server 1."
--		::= { swhSyslogConfiguration 13 }

--	swhLogServer2 OBJECT-TYPE
--		SYNTAX    DisplayString (SIZE (0..255))
--		ACCESS    read-write
--		STATUS    mandatory
--		DESCRIPTION
--			"log server 2."
--		::= { swhSyslogConfiguration 14 }

--	swhLogServer3 OBJECT-TYPE
--		SYNTAX    DisplayString (SIZE (0..255))
--		ACCESS    read-write
--		STATUS    mandatory
--		DESCRIPTION
--			"log server 3."
--		::= { swhSyslogConfiguration 15 }

	swhLoggingType
		OBJECT IDENTIFIER ::= { swhSyslogConfiguration 11 }

	swhLoggingTypeTerminalHistory OBJECT-TYPE
		SYNTAX    INTEGER { disable(0), enable(1) }
		ACCESS    read-write
		STATUS    mandatory
		DESCRIPTION
			"LoggingType's Terminal History ."
		::= { swhLoggingType 1 }


-- NetworkManagement(3).TimeRange(10)


-- SwitchManagement(4)

	swhSwitchConfiguration
		OBJECT IDENTIFIER ::= { swhSwitchManagement 1 }
	swhPortConfiguration
		OBJECT IDENTIFIER ::= { swhSwitchManagement 2 }
--	swhLinkAggregation
--		OBJECT IDENTIFIER ::= { swhSwitchManagement 45 }
--	swhSpanningTree
--		OBJECT IDENTIFIER ::= { swhSwitchManagement 40 }
	swh8021XConfiguration
		OBJECT IDENTIFIER ::= { swhSwitchManagement 55 }
	swhMacAddressManagement
		OBJECT IDENTIFIER ::= { swhSwitchManagement 35 }
	swhVLANConfiguration
		OBJECT IDENTIFIER ::= { swhSwitchManagement 4 }
	swhQoSConfiguration
		OBJECT IDENTIFIER ::= { swhSwitchManagement 60 }
	swhDSCPRemark
		OBJECT IDENTIFIER ::= { swhSwitchManagement 61 }
	swhPortMirroring
		OBJECT IDENTIFIER ::= { swhSwitchManagement 15 }
	swhIGMPSnooping
		OBJECT IDENTIFIER ::= { swhSwitchManagement 50 }
--	swhIGMPMVR
--		OBJECT IDENTIFIER ::= { swhSwitchManagement 92 }
	swhStaticMulticastConfiguration
		OBJECT IDENTIFIER ::= { swhSwitchManagement 70 }
	swhSecurityConfiguration
		OBJECT IDENTIFIER ::= { swhSwitchManagement 80 }
	swhACLConfiguration
		OBJECT IDENTIFIER ::= { swhSwitchManagement 65 }
--	swhLayer2ProtocolTunnel
--		OBJECT IDENTIFIER ::= { swhSwitchManagement 37 }
--	swhLLDPConfiguration
--		OBJECT IDENTIFIER ::= { swhSwitchManagement 14 }
	swhLoopDetection
		OBJECT IDENTIFIER ::= { swhSwitchManagement 13 }
--	swhRingDetection
--		OBJECT IDENTIFIER ::= { swhSwitchManagement 24 }
--	swhFastRedundancy
--		OBJECT IDENTIFIER ::= { swhSwitchManagement 91 }
--	swhDIConfiguration
--		OBJECT IDENTIFIER ::= { swhSwitchManagement 22 }
--	swhPOEConfiguration
--		OBJECT IDENTIFIER ::= { swhSwitchManagement 23 }
--	swhPoEManagementAndMonitor
--		OBJECT IDENTIFIER ::= { swhSwitchManagement 89 }
	swhLANFollowWAN
		OBJECT IDENTIFIER ::= { swhSwitchManagement 93 }


-- SwitchManagement(4).SwitchConfiguration(1)

	swhSwitchMaxFrameSize OBJECT-TYPE
		SYNTAX    INTEGER (1518..12288)
		ACCESS    read-write
		STATUS    mandatory
		DESCRIPTION
			"Max frame size."
		::= { swhSwitchConfiguration 1 }

	swhSwitchAgingTime OBJECT-TYPE
		SYNTAX    INTEGER (0..77925)
		ACCESS    read-write
		STATUS    mandatory
		DESCRIPTION
			"Mac address Aging time
			0 means never age out, 1-9 Days, 10-77925 Secs"
		::= { swhSwitchConfiguration 3 }

	swhSwitchStatisticsPollingPort OBJECT-TYPE
		SYNTAX    INTEGER
		ACCESS    read-write
		STATUS    mandatory
		DESCRIPTION
			"Statistics Counter Polling Port,1~Max(Units)."
		::= { swhSwitchConfiguration 54 }

	swhSwitchStatisticsPollingInterval OBJECT-TYPE
		SYNTAX    INTEGER
		ACCESS    read-write
		STATUS    mandatory
		DESCRIPTION
			"Statistics Counter Polling Interval,1-600(1/10 Sec)."
		::= { swhSwitchConfiguration 55 }


-- SwitchManagement(4).PortConfiguration(2)

	swhPortConfigTable OBJECT-TYPE
		SYNTAX    SEQUENCE OF SwhPortConfigEntry
		ACCESS    not-accessible
		STATUS    mandatory
		DESCRIPTION
			"Table of Port descriptive and status information."
		::= { swhPortConfiguration 1 }

	--swhSavePortConfiguration OBJECT-TYPE
	--	SYNTAX    INTEGER 
	--	ACCESS    write-only
	--	STATUS    mandatory
	--	DESCRIPTION
	--		"Save Port Configuration to Flash ROM"
	--	::= { swhPortConfiguration 2 }

	-- Table Entry
	swhPortConfigEntry OBJECT-TYPE
		SYNTAX    SwhPortConfigEntry
		ACCESS    not-accessible
		STATUS    mandatory
		DESCRIPTION
			"An entry in the table, containing information
			 about port config."
		INDEX    { swhPortConfigIndex }
		::= { swhPortConfigTable 1 }

	SwhPortConfigEntry ::=
		SEQUENCE {
			swhPortConfigIndex
				INTEGER,
			swhPortConfigMediaType
				INTEGER,
			swhPortConfigState
				INTEGER,
			swhPortConfigType
				INTEGER,
			swhPortConfigSpeed
				INTEGER,
			swhPortConfigDuplex
				INTEGER,
			swhPortConfigFlowControl
				INTEGER,
			swhPortConfigDescription
				DisplayString
		}

	swhPortConfigIndex OBJECT-TYPE
		SYNTAX    INTEGER (0..2147483647)
		ACCESS    not-accessible
		STATUS    mandatory
		DESCRIPTION
			"A unique value for each port."
		::= { swhPortConfigEntry 1 }

	swhPortConfigState OBJECT-TYPE
		SYNTAX    INTEGER { disable(0), enable(1) }
		ACCESS    read-write
		STATUS    mandatory
		DESCRIPTION
			"enable or disable port"
		::= { swhPortConfigEntry 2 }

	swhPortConfigType OBJECT-TYPE
		SYNTAX    INTEGER { auto-negotiation(0), manual(1) }
		ACCESS    read-write
		STATUS    mandatory
		DESCRIPTION
			"port type"
		::= { swhPortConfigEntry 3 }

	swhPortConfigSpeed OBJECT-TYPE
		SYNTAX    INTEGER { speed-10M(0), speed-100M(1), speed-1000M(2), auto-sense(3), speed-10G(4), speed-2500M(5), speed-5G(6) }
		ACCESS    read-write
		STATUS    mandatory
		DESCRIPTION
			"port Speed  10 100 1000 10G
			 it's configuration, NOT current speed, 
			 current speed is swhPortStatusSpeed under swhSwitchMonitor"
		::= { swhPortConfigEntry 4 }

	swhPortConfigDuplex OBJECT-TYPE
		SYNTAX    INTEGER { halfDuplex(0), fullDuplex(1) }
		ACCESS    read-write
		STATUS    mandatory
		DESCRIPTION
			"duplex
			 it's configuration, NOT current duplex, 
			 current duplex is swhPortStatusDuplex under swhSwitchMonitor"
		::= { swhPortConfigEntry 5 }

	swhPortConfigFlowControl OBJECT-TYPE
		SYNTAX    INTEGER { off(0), on(1) }
		ACCESS    read-write
		STATUS    mandatory
		DESCRIPTION
			"flow control"
		::= { swhPortConfigEntry 6 }

	swhPortConfigDescription OBJECT-TYPE
		SYNTAX    DisplayString
		ACCESS    read-write
		STATUS    mandatory
		DESCRIPTION
			"Port Description"
		::= { swhPortConfigEntry 7 }

	swhPortConfigMediaType OBJECT-TYPE
		SYNTAX    INTEGER { copper(0), fiber(1) }
		ACCESS    read-only
		STATUS    mandatory
		DESCRIPTION
			"Port Media Type"
		::= { swhPortConfigEntry 8 }


-- SwitchManagement(4).PriorityAndRateLimitConfiguration(3)


-- SwitchManagement(4).VLANConfiguration(4)

	swhPortVLANConfiguration
		OBJECT IDENTIFIER ::= { swhVLANConfiguration 1 }

	swh8021QVLANConfiguration
		OBJECT IDENTIFIER ::= { swhVLANConfiguration 2 }

	swhVLANTranslationConfiguration
		OBJECT IDENTIFIER ::= { swhVLANConfiguration 7 }

	swhSelectiveQinQConfiguration
		OBJECT IDENTIFIER ::= { swhVLANConfiguration 9 }

--	swhQinQVLANConfiguration
--		OBJECT IDENTIFIER ::= { swhVLANConfiguration 5 }


-- SwitchManagement(4).VLANConfiguration(4).PortVLANConfiguration(1)

	swhPortVLANConfigTable OBJECT-TYPE
		SYNTAX    SEQUENCE OF SwhPortVLANConfigEntry
		ACCESS    not-accessible
		STATUS    mandatory
		DESCRIPTION
			"Table of Port Based VLAN Configuration."
		::= { swhPortVLANConfiguration 1 }

	-- Table Entry
	swhPortVLANConfigEntry OBJECT-TYPE
		SYNTAX    SwhPortVLANConfigEntry
		ACCESS    not-accessible
		STATUS    mandatory
		DESCRIPTION
			"An entry in the table, containing information
			 about port based vlan config."
		INDEX    { swhPortVLANConfigIndex }
		::= { swhPortVLANConfigTable 1 }

	SwhPortVLANConfigEntry ::=
		SEQUENCE {
			swhPortVLANConfigIndex
				INTEGER,
			swhPortVLANConfigValid
				INTEGER,
			swhPortVLANConfigName
				DisplayString,
			swhPortVLANConfigPort1
				INTEGER,
			swhPortVLANConfigPort2
				INTEGER,
			swhPortVLANConfigPort3
				INTEGER,
			swhPortVLANConfigPort4
				INTEGER,
			swhPortVLANConfigPort5
				INTEGER,
			swhPortVLANConfigPort6
				INTEGER,
			swhPortVLANConfigCPU
				INTEGER,
			swhPortVLANConfigDelete
				INTEGER
		}

	swhPortVLANConfigIndex OBJECT-TYPE
		SYNTAX    INTEGER (0..2147483647)
		ACCESS    not-accessible
		STATUS    mandatory
		DESCRIPTION
			"A unique value for each vlan."
		::= { swhPortVLANConfigEntry 1 }

	swhPortVLANConfigValid OBJECT-TYPE
		SYNTAX    INTEGER { invalid(0), valid(1) }
		ACCESS    read-only
		STATUS    mandatory
		DESCRIPTION
			"This vlan setting is valid or invalid."
		::= { swhPortVLANConfigEntry 2 }

	swhPortVLANConfigName OBJECT-TYPE
		SYNTAX    DisplayString
		ACCESS    read-write
		STATUS    mandatory
		DESCRIPTION
			"Port based vlan name."
		::= { swhPortVLANConfigEntry 4 }

	swhPortVLANConfigPort1 OBJECT-TYPE
		SYNTAX    INTEGER { b(0), v(1) }
		ACCESS    read-write
		STATUS    mandatory
		DESCRIPTION
			"b:Blocked  v:Member"
		::= { swhPortVLANConfigEntry 5 }

	swhPortVLANConfigPort2 OBJECT-TYPE
		SYNTAX    INTEGER { b(0), v(1) }
		ACCESS    read-write
		STATUS    mandatory
		DESCRIPTION
			"b:Blocked  v:Member"
		::= { swhPortVLANConfigEntry 6 }

	swhPortVLANConfigPort3 OBJECT-TYPE
		SYNTAX    INTEGER { b(0), v(1) }
		ACCESS    read-write
		STATUS    mandatory
		DESCRIPTION
			"b:Blocked  v:Member"
		::= { swhPortVLANConfigEntry 7 }

	swhPortVLANConfigPort4 OBJECT-TYPE
		SYNTAX    INTEGER { b(0), v(1) }
		ACCESS    read-write
		STATUS    mandatory
		DESCRIPTION
			"b:Blocked  v:Member"
		::= { swhPortVLANConfigEntry 8 }

	swhPortVLANConfigPort5 OBJECT-TYPE
		SYNTAX    INTEGER { b(0), v(1) }
		ACCESS    read-write
		STATUS    mandatory
		DESCRIPTION
			"b:Blocked  v:Member"
		::= { swhPortVLANConfigEntry 9 }

	swhPortVLANConfigPort6 OBJECT-TYPE
		SYNTAX    INTEGER { b(0), v(1) }
		ACCESS    read-write
		STATUS    mandatory
		DESCRIPTION
			"b:Blocked  v:Member"
		::= { swhPortVLANConfigEntry 10 }

	swhPortVLANConfigCPU OBJECT-TYPE
		SYNTAX    INTEGER { b(0), v(1) }
		ACCESS    read-write
		STATUS    mandatory
		DESCRIPTION
			"b:Blocked  v:Member"
		::= { swhPortVLANConfigEntry 55 }

	swhPortVLANConfigDelete OBJECT-TYPE
		SYNTAX    INTEGER { normal(0), delete(1) }
		ACCESS    read-write
		STATUS    mandatory
		DESCRIPTION
			"Delete this vlan setting."
		::= { swhPortVLANConfigEntry 56 }


-- SwitchManagement(4).VLANConfiguration(4).8021QVLANConfiguration(2)

	swh8021QTrunkVLAN
		OBJECT IDENTIFIER ::= { swh8021QVLANConfiguration 1 }

	swh8021QPortVLANConfig
		OBJECT IDENTIFIER ::= { swh8021QVLANConfiguration 2 }

	swh8021QManagementVLANConfig
		OBJECT IDENTIFIER ::= { swh8021QVLANConfiguration 5 }


-- SwitchManagement(4).VLANConfiguration(4).8021QVLANConfiguration(2).8021QTrunkVLAN(1)

	swh8021QTrunkVLANTable OBJECT-TYPE
		SYNTAX    SEQUENCE OF Swh8021QTrunkVLANEntry
		ACCESS    not-accessible
		STATUS    mandatory
		DESCRIPTION
			"Table of 802.1Q Trunk VLAN Configuration."
		::= { swh8021QTrunkVLAN 1 }

	-- Table Entry
	swh8021QTrunkVLANEntry OBJECT-TYPE
		SYNTAX    Swh8021QTrunkVLANEntry
		ACCESS    not-accessible
		STATUS    mandatory
		DESCRIPTION
			"An entry in the table, containing information
			about trunk vlan config."
		INDEX    { swh8021QTrunkVLANIndex }
		::= { swh8021QTrunkVLANTable 1 }

	Swh8021QTrunkVLANEntry ::=
		SEQUENCE {
			swh8021QTrunkVLANIndex
				INTEGER,
			swh8021QTrunkVLANValid
				INTEGER,
			swh8021QTrunkVLANVID
				INTEGER,
			swh8021QTrunkVLANName
				DisplayString,
			swh8021QTrunkVLANPort1
				INTEGER,
			swh8021QTrunkVLANPort2
				INTEGER,
			swh8021QTrunkVLANPort3
				INTEGER,
			swh8021QTrunkVLANPort4
				INTEGER,
			swh8021QTrunkVLANPort5
				INTEGER,
			swh8021QTrunkVLANPort6
				INTEGER,
			swh8021QTrunkVLANCPU
				INTEGER,
			swh8021QTrunkVLANDelete
				INTEGER
		}

	swh8021QTrunkVLANIndex OBJECT-TYPE
		SYNTAX    INTEGER (0..2147483647)
		ACCESS    not-accessible
		STATUS    mandatory
		DESCRIPTION
			"A unique value for each vlan."
		::= { swh8021QTrunkVLANEntry 1 }

	swh8021QTrunkVLANValid OBJECT-TYPE
		SYNTAX    INTEGER { invalid(0), valid(1) }
		ACCESS    read-only
		STATUS    mandatory
		DESCRIPTION
			"This vlan setting is valid or invalid."
		::= { swh8021QTrunkVLANEntry 2 }

	swh8021QTrunkVLANVID OBJECT-TYPE
		SYNTAX    INTEGER (1..4094)
		ACCESS    read-write
		STATUS    mandatory
		DESCRIPTION
			"VLAN ID"
		::= { swh8021QTrunkVLANEntry 3 }

	swh8021QTrunkVLANName OBJECT-TYPE
		SYNTAX    DisplayString
		ACCESS    read-write
		STATUS    mandatory
		DESCRIPTION
			"Port based vlan name."
		::= { swh8021QTrunkVLANEntry 4 }

	swh8021QTrunkVLANPort1 OBJECT-TYPE
		SYNTAX    INTEGER { b(0), v(1) }
		ACCESS    read-write
		STATUS    mandatory
		DESCRIPTION
			"b:Blocked  v:Member"
		::= { swh8021QTrunkVLANEntry 5 }

	swh8021QTrunkVLANPort2 OBJECT-TYPE
		SYNTAX    INTEGER { b(0), v(1) }
		ACCESS    read-write
		STATUS    mandatory
		DESCRIPTION
			"b:Blocked  v:Member"
		::= { swh8021QTrunkVLANEntry 6 }

	swh8021QTrunkVLANPort3 OBJECT-TYPE
		SYNTAX    INTEGER { b(0), v(1) }
		ACCESS    read-write
		STATUS    mandatory
		DESCRIPTION
			"b:Blocked  v:Member"
		::= { swh8021QTrunkVLANEntry 7 }

	swh8021QTrunkVLANPort4 OBJECT-TYPE
		SYNTAX    INTEGER { b(0), v(1) }
		ACCESS    read-write
		STATUS    mandatory
		DESCRIPTION
			"b:Blocked  v:Member"
		::= { swh8021QTrunkVLANEntry 8 }

	swh8021QTrunkVLANPort5 OBJECT-TYPE
		SYNTAX    INTEGER { b(0), v(1) }
		ACCESS    read-write
		STATUS    mandatory
		DESCRIPTION
			"b:Blocked  v:Member"
		::= { swh8021QTrunkVLANEntry 9 }

	swh8021QTrunkVLANPort6 OBJECT-TYPE
		SYNTAX    INTEGER { b(0), v(1) }
		ACCESS    read-write
		STATUS    mandatory
		DESCRIPTION
			"b:Blocked  v:Member"
		::= { swh8021QTrunkVLANEntry 10 }

	swh8021QTrunkVLANCPU OBJECT-TYPE
		SYNTAX    INTEGER { b(0), v(1) }
		ACCESS    read-only
		STATUS    mandatory
		DESCRIPTION
			"b:Blocked  v:Member"
		::= { swh8021QTrunkVLANEntry 55 }

	swh8021QTrunkVLANDelete OBJECT-TYPE
		SYNTAX    INTEGER { normal(0), delete(1) }
		ACCESS    read-write
		STATUS    mandatory
		DESCRIPTION
			"Delete this vlan setting."
		::= { swh8021QTrunkVLANEntry 56 }


-- SwitchManagement(4).VLANConfiguration(4).8021QVLANConfiguration(2).8021QPortVLANConfig(2)

	swh8021QTunnelEtherType OBJECT-TYPE
		SYNTAX    DisplayString
		ACCESS    read-write
		STATUS    mandatory
		DESCRIPTION
			"802.1Q Tunnel Ether Type; 0x0000-0xFFFF"
		::= { swh8021QPortVLANConfig 14 }

-- SwitchManagement(4).VLANConfiguration(4).8021QVLANConfiguration(2).8021QPortVLANConfig(2).8021QPortVLANConfigTable(2)

	swh8021QPortVLANConfigTable OBJECT-TYPE
		SYNTAX    SEQUENCE OF Swh8021QPortVLANConfigEntry
		ACCESS    not-accessible
		STATUS    mandatory
		DESCRIPTION
			"Table of 802.1q VLAN ID."
		::= { swh8021QPortVLANConfig 2 }

	-- Table Entry
	swh8021QPortVLANConfigEntry OBJECT-TYPE
		SYNTAX    Swh8021QPortVLANConfigEntry
		ACCESS    not-accessible
		STATUS    mandatory
		DESCRIPTION
			"An entry in the table, containing information
			about Port VLAN ID "
		INDEX    { swh8021QPortIndex }
		::= { swh8021QPortVLANConfigTable 1 }

	Swh8021QPortVLANConfigEntry ::=
		SEQUENCE {
			swh8021QPortIndex
				INTEGER,
			swh8021QPortVLANMode
				INTEGER,
			swh8021QPortAccessVLAN
				INTEGER,
			swh8021QPortTrunkVLAN
				DisplayString
		}

	swh8021QPortIndex OBJECT-TYPE
		SYNTAX    INTEGER (0..2147483647)
		ACCESS    not-accessible
		STATUS    mandatory
		DESCRIPTION
			"A unique value for port index."
		::= { swh8021QPortVLANConfigEntry 1 }

	swh8021QPortAccessVLAN OBJECT-TYPE
		SYNTAX    INTEGER (1..4094)
		ACCESS    read-write
		STATUS    mandatory
		DESCRIPTION
			"Port Access VLAN ID(1-4094)."
		::= { swh8021QPortVLANConfigEntry 2 }

	swh8021QPortVLANMode OBJECT-TYPE
		SYNTAX    INTEGER { access(0), trunk(1), trunknative(2), dot1qtunnel(3), selectiveqinq(4) }
		ACCESS    read-write
		STATUS    mandatory
		DESCRIPTION
			"Port VLAN mode."
		::= { swh8021QPortVLANConfigEntry 20 }

	swh8021QPortTrunkVLAN OBJECT-TYPE
		SYNTAX    DisplayString
		ACCESS    read-write
		STATUS    mandatory
		DESCRIPTION
			"Port Trunk VLAN ID member(1-4094)."
		::= { swh8021QPortVLANConfigEntry 25 }


-- SwitchManagement(4).VLANConfiguration(4).8021QVLANConfiguration(2).8021QPortVLANConfig(2).8021QVLANTranslation(15)


-- SwitchManagement(4).VLANConfiguration(4).8021QVLANConfiguration(2).8021QPortVLANConfig(3)


-- SwitchManagement(4).VLANConfiguration(4).8021QVLANConfiguration(2).8021QManagementVLANConfig(5)

	swh8021QManagementVLANConfigCPUVID OBJECT-TYPE
		SYNTAX    INTEGER (1..4094) 
		ACCESS    read-write
		STATUS    mandatory
		DESCRIPTION
			"CPU VLAN ID.(1-4094)"
		::= { swh8021QManagementVLANConfig 1 }

	swh8021QManagementVLANConfigVLANMode OBJECT-TYPE
		SYNTAX    INTEGER { access(0), trunk(1), trunknative(2) }
		ACCESS    read-write
		STATUS    mandatory
		DESCRIPTION
			"Aware is disable or enable"
		::= { swh8021QManagementVLANConfig 3 }

	swh8021QManagementVLANConfigPort1 OBJECT-TYPE
		SYNTAX    INTEGER { b(0), v(1) }
		ACCESS    read-write
		STATUS    mandatory
		DESCRIPTION
			"b:Blocked  v:Member"
		::= { swh8021QManagementVLANConfig 5 }

	swh8021QManagementVLANConfigPort2 OBJECT-TYPE
		SYNTAX    INTEGER { b(0), v(1) }
		ACCESS    read-write
		STATUS    mandatory
		DESCRIPTION
			"b:Blocked  v:Member"
		::= { swh8021QManagementVLANConfig 6 }

	swh8021QManagementVLANConfigPort3 OBJECT-TYPE
		SYNTAX    INTEGER { b(0), v(1) }
		ACCESS    read-write
		STATUS    mandatory
		DESCRIPTION
			"b:Blocked  v:Member"
		::= { swh8021QManagementVLANConfig 7 }

	swh8021QManagementVLANConfigPort4 OBJECT-TYPE
		SYNTAX    INTEGER { b(0), v(1) }
		ACCESS    read-write
		STATUS    mandatory
		DESCRIPTION
			"b:Blocked  v:Member"
		::= { swh8021QManagementVLANConfig 8 }

	swh8021QManagementVLANConfigPort5 OBJECT-TYPE
		SYNTAX    INTEGER { b(0), v(1) }
		ACCESS    read-write
		STATUS    mandatory
		DESCRIPTION
			"b:Blocked  v:Member"
		::= { swh8021QManagementVLANConfig 9 }

	swh8021QManagementVLANConfigPort6 OBJECT-TYPE
		SYNTAX    INTEGER { b(0), v(1) }
		ACCESS    read-write
		STATUS    mandatory
		DESCRIPTION
			"b:Blocked  v:Member"
		::= { swh8021QManagementVLANConfig 10 }


-- SwitchManagement(4).VLANConfiguration(4).8021QVLANConfiguration(2).8021QTransVID(8)


-- SwitchManagement(4).VLANConfiguration(4).8021QVLANConfiguration(2).8021QTransVID(8).8021QTransVIDTable(2)


-- SwitchManagement(4).VLANConfiguration(4).QinQVLANConfiguration(5)

--	swhQinQVLANMode OBJECT-TYPE
--		SYNTAX    INTEGER { disable(0), enable(1) }
--		ACCESS    read-write
--		STATUS    mandatory
--		DESCRIPTION
--			"QinQ Mode"
--		::= { swhQinQVLANConfiguration 1 }

--	swhQinQVLANEtherType OBJECT-TYPE
--		SYNTAX    DisplayString
--		ACCESS    read-write
--		STATUS    mandatory
--		DESCRIPTION
--			"QinQ VLAN Ether Type; 0x0000-0xFFFF"
--		::= { swhQinQVLANConfiguration 2 }

--	swhQinQVLANPassThroughMode OBJECT-TYPE
--		SYNTAX    INTEGER { disable(0), enable(1) }
--		ACCESS    read-write
--		STATUS    mandatory
--		DESCRIPTION
--			"QinQ Pass Through Mode"
--		::= { swhQinQVLANConfiguration 57 }

--	swhQinQVLANPassThroughVID OBJECT-TYPE
--		SYNTAX    INTEGER (1..4094)
--		ACCESS    read-write
--		STATUS    mandatory
--		DESCRIPTION
--			"QinQ Pass Through VLAN ID(1-4094)"
--		::= { swhQinQVLANConfiguration 59 }


-- SwitchManagement(4).VLANConfiguration(4).QinQVLANConfiguration(5).QinQVLANConfigTable(60)

--	swhQinQVLANConfigTable OBJECT-TYPE
--		SYNTAX    SEQUENCE OF SWHQinQVLANConfigEntry
--		ACCESS    not-accessible
--		STATUS    mandatory
--		DESCRIPTION
--			"Table of 802.1q VLAN ID."
--		::= { swhQinQVLANConfiguration 60 }

	-- Table Entry
--	swhQinQVLANConfigEntry OBJECT-TYPE
--		SYNTAX    SWHQinQVLANConfigEntry
--		ACCESS    not-accessible
--		STATUS    mandatory
--		DESCRIPTION
--			"An entry in the table, containing information
--			 about QinQ VLAN Config"
--		INDEX    { swhQinQVLANPortIndex }
--		::= { swhQinQVLANConfigTable 1 }

--	SWHQinQVLANConfigEntry ::=
--		SEQUENCE {
--			swhQinQVLANPortIndex
--				INTEGER,
--			swhQinQVLANPortName
--				DisplayString,
--			swhQinQVLANPortStagVID
--				INTEGER,
--			swhQinQVLANPortISPPort
--				INTEGER
--		}

--	swhQinQVLANPortIndex OBJECT-TYPE
--		SYNTAX    INTEGER (0..2147483647)
--		ACCESS    not-accessible
--		STATUS    mandatory
--		DESCRIPTION
--			"A unique value for port index."
--		::= { swhQinQVLANConfigEntry 1 }

--	swhQinQVLANPortName OBJECT-TYPE
--		SYNTAX    DisplayString
--		ACCESS    read-only
--		STATUS    mandatory
--		DESCRIPTION
--			"Port Name"
--		::= { swhQinQVLANConfigEntry 3 }

--	swhQinQVLANPortStagVID OBJECT-TYPE
--		SYNTAX    INTEGER (1..4094)
--		ACCESS    read-write
--		STATUS    mandatory
--		DESCRIPTION
--			"Specify port Stag VLAN ID(1-4094)."
--		::= { swhQinQVLANConfigEntry 6 }

--	swhQinQVLANPortISPPort OBJECT-TYPE
--		SYNTAX    INTEGER { b(0), v(1) }
--		ACCESS    read-write
--		STATUS    mandatory
--		DESCRIPTION
--			"b:Blocked  v:Member"
--		::= { swhQinQVLANConfigEntry 7 }


-- SwitchManagement(4).VLANConfiguration(4).QinQVLANConfiguration(5).QinQVLANManagementStagVID(61)

--	swhQinQVLANManagementStagVID OBJECT-TYPE
--		SYNTAX    INTEGER (1..4094)
--		ACCESS    read-write
--		STATUS    mandatory
--		DESCRIPTION
--			"QinQ Management Stag VLAN ID(1-4094)"
--		::= { swhQinQVLANConfiguration 61 }


-- SwitchManagement(4).VLANConfiguration(4).PortIsolationConfiguration(6)


-- SwitchManagement(4).VLANConfiguration(4).VLANTranslationConfiguration(7)

	swhVLANTranslationConfigVLANTranslation OBJECT-TYPE
		SYNTAX    INTEGER { disable(0), enable(1) }
		ACCESS    read-write
		STATUS    mandatory
		DESCRIPTION
			"Enable or Disable VLAN Translation"
		::= { swhVLANTranslationConfiguration 1 }


-- SwitchManagement(4).VLANConfiguration(4).VLANTranslationConfiguration(7).VLANTranslationConfigTable(5)

	swhVLANTranslationConfigTable OBJECT-TYPE
		SYNTAX    SEQUENCE OF SwhVLANTranslationConfigEntry
		ACCESS    not-accessible
		STATUS    mandatory
		DESCRIPTION
			"Table of VLAN Translation."
		::= { swhVLANTranslationConfiguration 5 }

	-- Table Entry
	swhVLANTranslationConfigEntry OBJECT-TYPE
		SYNTAX    SwhVLANTranslationConfigEntry
		ACCESS    not-accessible
		STATUS    mandatory
		DESCRIPTION
			"An entry in the table, containing information
			about VLAN Translation"
		INDEX    { swhVLANTranslationConfigIndex }
		::= { swhVLANTranslationConfigTable 1 }

	SwhVLANTranslationConfigEntry ::=
		SEQUENCE {
			swhVLANTranslationConfigIndex
				INTEGER,
			swhVLANTranslationConfigValid
				INTEGER,
			swhVLANTranslationConfigName
				DisplayString,
			swhVLANTranslationConfigPort
				INTEGER,
			swhVLANTranslationConfigOriginalVID
				INTEGER,
			swhVLANTranslationConfigMappedVID
				INTEGER,
			swhVLANTranslationConfigPriority
				INTEGER,
			swhVLANTranslationConfigDelete
				INTEGER
		}

	swhVLANTranslationConfigIndex OBJECT-TYPE
		SYNTAX    INTEGER (0..2147483647)
		ACCESS    not-accessible
		STATUS    mandatory
		DESCRIPTION
			"A unique value for port index."
		::= { swhVLANTranslationConfigEntry 1 }

	swhVLANTranslationConfigValid OBJECT-TYPE
		SYNTAX    INTEGER { invalid(0), valid(1) }
		ACCESS    read-only
		STATUS    mandatory
		DESCRIPTION
			"This entry is valid or invalid."
		::= { swhVLANTranslationConfigEntry 2 }

	swhVLANTranslationConfigName OBJECT-TYPE
		SYNTAX    DisplayString
		ACCESS    read-write
		STATUS    mandatory
		DESCRIPTION
			"VLAN Translation Name"
		::= { swhVLANTranslationConfigEntry 4 }

	swhVLANTranslationConfigPort OBJECT-TYPE
		SYNTAX    INTEGER { port01(0),
		                    port02(1),
		                    port03(2),
		                    port04(3),
		                    port05(4),
		                    port06(5)
		                    }
		ACCESS    read-write
		STATUS    mandatory
		DESCRIPTION
			"Port Number."
		::= { swhVLANTranslationConfigEntry 5 }

	swhVLANTranslationConfigOriginalVID OBJECT-TYPE
		SYNTAX    INTEGER (1..4094)
		ACCESS    read-write
		STATUS    mandatory
		DESCRIPTION
			"Specify Original VLAN ID(1-4094)."
		::= { swhVLANTranslationConfigEntry 6 }

	swhVLANTranslationConfigMappedVID OBJECT-TYPE
		SYNTAX    INTEGER (1..4094)
		ACCESS    read-write
		STATUS    mandatory
		DESCRIPTION
			"Specify Translated VLAN ID(1-4094)."
		::= { swhVLANTranslationConfigEntry 7 }

	swhVLANTranslationConfigPriority OBJECT-TYPE
		SYNTAX    INTEGER (0..7)
		ACCESS    read-write
		STATUS    mandatory
		DESCRIPTION
			"Specify Priority(0-7)."
		::= { swhVLANTranslationConfigEntry 8 }

	swhVLANTranslationConfigDelete OBJECT-TYPE
		SYNTAX    INTEGER { normal(0), delete(1) }
		ACCESS    read-write
		STATUS    mandatory
		DESCRIPTION
			"Delete this entry."
		::= { swhVLANTranslationConfigEntry 10 }


-- SwitchManagement(4).VLANConfiguration(4).SelectiveQinQConfiguration(9)

	swhSelectiveQinQConfigSelectiveQinQ OBJECT-TYPE
		SYNTAX    INTEGER { disable(0), enable(1) }
		ACCESS    read-write
		STATUS    mandatory
		DESCRIPTION
			"Enable or Disable Selective QinQ"
		::= { swhSelectiveQinQConfiguration 1 }

	swhSelectiveQinQConfigSelectiveQinQSortBy OBJECT-TYPE
		SYNTAX    INTEGER { entry(0), port(1), inner-vid(2), outer-vid(3) }
		ACCESS    read-write
		STATUS    mandatory
		DESCRIPTION
			"Selective QinQ SortBy"
		::= { swhSelectiveQinQConfiguration 3 }

	swhSelectiveQinQConfigSelectiveQinQDefaultTPID OBJECT-TYPE
		SYNTAX    DisplayString
		ACCESS    read-only
		STATUS    mandatory
		DESCRIPTION
			"Default TPID 0x0000-0xFFFF"
		::= { swhSelectiveQinQConfiguration 6 }

	swhSelectiveQinQConfigSelectiveQinQTPID1 OBJECT-TYPE
		SYNTAX    DisplayString
		ACCESS    read-write
		STATUS    mandatory
		DESCRIPTION
			"TPID1 0x0000-0xFFFF"
		::= { swhSelectiveQinQConfiguration 7 }

	swhSelectiveQinQConfigSelectiveQinQTPID2 OBJECT-TYPE
		SYNTAX    DisplayString
		ACCESS    read-write
		STATUS    mandatory
		DESCRIPTION
			"TPID2 0x0000-0xFFFF"
		::= { swhSelectiveQinQConfiguration 8 }

	swhSelectiveQinQConfigSelectiveQinQTPID3 OBJECT-TYPE
		SYNTAX    DisplayString
		ACCESS    read-write
		STATUS    mandatory
		DESCRIPTION
			"TPID3"
		::= { swhSelectiveQinQConfiguration 9 }


-- SwitchManagement(4).VLANConfiguration(4).SelectiveQinQConfiguration(9).SelectiveQinQConfigTable(5)

	swhSelectiveQinQConfigTable OBJECT-TYPE
		SYNTAX    SEQUENCE OF SwhSelectiveQinQConfigEntry
		ACCESS    not-accessible
		STATUS    mandatory
		DESCRIPTION
			"Table of Selective QinQ."
		::= { swhSelectiveQinQConfiguration 5 }

	-- Table Entry
	swhSelectiveQinQConfigEntry OBJECT-TYPE
		SYNTAX    SwhSelectiveQinQConfigEntry
		ACCESS    not-accessible
		STATUS    mandatory
		DESCRIPTION
			"An entry in the table, containing information
			about Selective QinQ"
		INDEX    { swhSelectiveQinQConfigIndex }
		::= { swhSelectiveQinQConfigTable 1 }

	SwhSelectiveQinQConfigEntry ::=
		SEQUENCE {
			swhSelectiveQinQConfigIndex
				INTEGER,
			swhSelectiveQinQConfigConfigEntry
				INTEGER,
			swhSelectiveQinQConfigValid
				INTEGER,
			swhSelectiveQinQConfigName
				DisplayString,
			swhSelectiveQinQConfigPort
				DisplayString,
			swhSelectiveQinQConfigInnerVID
				DisplayString,
			swhSelectiveQinQConfigOuterVID
				INTEGER,
			swhSelectiveQinQConfigTPID
				INTEGER,
			swhSelectiveQinQConfigEtherType
				DisplayString,
			swhSelectiveQinQConfigPriority
				INTEGER,
			swhSelectiveQinQConfigDelete
				INTEGER
		}

	swhSelectiveQinQConfigIndex OBJECT-TYPE
		SYNTAX    INTEGER (0..2147483647)
		ACCESS    not-accessible
		STATUS    mandatory
		DESCRIPTION
			"A unique value for port index."
		::= { swhSelectiveQinQConfigEntry 1 }

	swhSelectiveQinQConfigValid OBJECT-TYPE
		SYNTAX    INTEGER { invalid(0), valid(1) }
		ACCESS    read-only
		STATUS    mandatory
		DESCRIPTION
			"This entry is valid or invalid."
		::= { swhSelectiveQinQConfigEntry 2 }

	swhSelectiveQinQConfigName OBJECT-TYPE
		SYNTAX    DisplayString
		ACCESS    read-write
		STATUS    mandatory
		DESCRIPTION
			"Selective QinQ Name"
		::= { swhSelectiveQinQConfigEntry 4 }

	swhSelectiveQinQConfigPort OBJECT-TYPE
		SYNTAX    DisplayString
		ACCESS    read-write
		STATUS    mandatory
		DESCRIPTION
			"Port Number."
		::= { swhSelectiveQinQConfigEntry 5 }

	swhSelectiveQinQConfigInnerVID OBJECT-TYPE
		SYNTAX    DisplayString
		ACCESS    read-write
		STATUS    mandatory
		DESCRIPTION
			"Specify Original VLAN ID(1-4094)."
		::= { swhSelectiveQinQConfigEntry 6 }

	swhSelectiveQinQConfigOuterVID OBJECT-TYPE
		SYNTAX    INTEGER (1..4094)
		ACCESS    read-write
		STATUS    mandatory
		DESCRIPTION
			"Specify Selective QinQ ID(1-4094)."
		::= { swhSelectiveQinQConfigEntry 7 }

	swhSelectiveQinQConfigTPID OBJECT-TYPE
		SYNTAX    INTEGER { default-tpid(0), tpid1(1), tpid2(2), tpid3(3) }
		ACCESS    read-write
		STATUS    mandatory
		DESCRIPTION
			"Specify TPID(0-3)."
		::= { swhSelectiveQinQConfigEntry 8 }

	swhSelectiveQinQConfigPriority OBJECT-TYPE
		SYNTAX    INTEGER (0..7)
		ACCESS    read-write
		STATUS    mandatory
		DESCRIPTION
			"Specify Priority(0-7)."
		::= { swhSelectiveQinQConfigEntry 9 }

	swhSelectiveQinQConfigDelete OBJECT-TYPE
		SYNTAX    INTEGER { normal(0), delete(1) }
		ACCESS    read-write
		STATUS    mandatory
		DESCRIPTION
			"Delete this entry."
		::= { swhSelectiveQinQConfigEntry 10 }

	swhSelectiveQinQConfigConfigEntry OBJECT-TYPE
		SYNTAX    INTEGER (0..2147483647)
		ACCESS    read-only
		STATUS    mandatory
		DESCRIPTION
			"A unique value for Selective QinQ entry."
		::= { swhSelectiveQinQConfigEntry 11 }

	swhSelectiveQinQConfigEtherType OBJECT-TYPE
		SYNTAX    DisplayString
		ACCESS    read-only
		STATUS    mandatory
		DESCRIPTION
			"Specify EtherType."
		::= { swhSelectiveQinQConfigEntry 12 }


-- SwitchManagement(4).SpanningTreeProtocol(9)


-- SwitchManagement(4).RateLimiting(10)


-- SwitchManagement(4).L2ProtocolConverting(11)


-- SwitchManagement(4).CDPConfiguration(12)


-- SwitchManagement(4).LoopDetection(13)

	swhLoopConfigLoopDetection OBJECT-TYPE
		SYNTAX    INTEGER { disable(0), enable(1) }
		ACCESS    read-write
		STATUS    mandatory
		DESCRIPTION
			"Loop Detection is disable or enable."
		::= { swhLoopDetection 60 }

	swhLoopConfigDetectionInterval OBJECT-TYPE
		SYNTAX    INTEGER (1..180)
		ACCESS    read-write
		STATUS    mandatory
		DESCRIPTION
			"Sending Detected Interval(1-180 Secs)"
		::= { swhLoopDetection 63 }

	swhLoopConfigUnlockInterval OBJECT-TYPE
		SYNTAX    INTEGER (1..1440)
		ACCESS    read-write
		STATUS    mandatory
		DESCRIPTION
			"Looped port unlock-interval(1-1440 Mins).
			Set the interval to check the port is loop-free or not"
		::= { swhLoopDetection 64 }

	swhLoopConfigAllVLAN OBJECT-TYPE
		SYNTAX    INTEGER { disable(0), enable(1) }
		ACCESS    read-write
		STATUS    mandatory
		DESCRIPTION
			"All VLAN is disable or enable."
		::= { swhLoopDetection 69 }

	swhLoopConfigVLAN1 OBJECT-TYPE
		SYNTAX    INTEGER (1..4096)
		ACCESS    read-write
		STATUS    mandatory
		DESCRIPTION
			"Sending Detected VLAN ID(1-4096)"
		::= { swhLoopDetection 65 }

	swhLoopConfigVLAN2 OBJECT-TYPE
		SYNTAX    INTEGER (1..4096)
		ACCESS    read-write
		STATUS    mandatory
		DESCRIPTION
			"Sending Detected VLAN ID(1-4096)"
		::= { swhLoopDetection 66 }

	swhLoopConfigVLAN3 OBJECT-TYPE
		SYNTAX    INTEGER (1..4096)
		ACCESS    read-write
		STATUS    mandatory
		DESCRIPTION
			"Sending Detected VLAN ID(1-4096)"
		::= { swhLoopDetection 67 }

	swhLoopConfigVLAN4 OBJECT-TYPE
		SYNTAX    INTEGER (1..4096)
		ACCESS    read-write
		STATUS    mandatory
		DESCRIPTION
			"Sending Detected VLAN ID(1-4096)"
		::= { swhLoopDetection 68 }

	swhLoopConfigPort1 OBJECT-TYPE
		SYNTAX    INTEGER { b(0), v(1) }
		ACCESS    read-write
		STATUS    mandatory
		DESCRIPTION
			"b:Blocked  v:Member"
		::= { swhLoopDetection 1 }

	swhLoopConfigPort2 OBJECT-TYPE
		SYNTAX    INTEGER { b(0), v(1) }
		ACCESS    read-write
		STATUS    mandatory
		DESCRIPTION
			"b:Blocked  v:Member"
		::= { swhLoopDetection 2 }

	swhLoopConfigPort3 OBJECT-TYPE
		SYNTAX    INTEGER { b(0), v(1) }
		ACCESS    read-write
		STATUS    mandatory
		DESCRIPTION
			"b:Blocked  v:Member"
		::= { swhLoopDetection 3 }

	swhLoopConfigPort4 OBJECT-TYPE
		SYNTAX    INTEGER { b(0), v(1) }
		ACCESS    read-write
		STATUS    mandatory
		DESCRIPTION
			"b:Blocked  v:Member"
		::= { swhLoopDetection 4 }

	swhLoopConfigPort5 OBJECT-TYPE
		SYNTAX    INTEGER { b(0), v(1) }
		ACCESS    read-write
		STATUS    mandatory
		DESCRIPTION
			"b:Blocked  v:Member"
		::= { swhLoopDetection 5 }

	swhLoopConfigPort6 OBJECT-TYPE
		SYNTAX    INTEGER { b(0), v(1) }
		ACCESS    read-write
		STATUS    mandatory
		DESCRIPTION
			"b:Blocked  v:Member"
		::= { swhLoopDetection 6 }


-- SwitchManagement(4).LoopDetection(13).LoopConfigTable(80)


-- SwitchManagement(4).LLDPConfiguration(14)

--	swhLLDPConfigEnable OBJECT-TYPE
--		SYNTAX    INTEGER { disable(0), enable(1) }
--		ACCESS    read-write
--		STATUS    mandatory
--		DESCRIPTION
--			"disable:0  enable:1"
--		::= { swhLLDPConfiguration 100 }
--
--	swhLLDPConfigPort1 OBJECT-TYPE
--		SYNTAX    INTEGER { b(0), v(1) }
--		ACCESS    read-write
--		STATUS    mandatory
--		DESCRIPTION
--			"b:Blocked  v:Member"
--		::= { swhLLDPConfiguration 1 }
--
--	swhLLDPConfigPort2 OBJECT-TYPE
--		SYNTAX    INTEGER { b(0), v(1) }
--		ACCESS    read-write
--		STATUS    mandatory
--		DESCRIPTION
--			"b:Blocked  v:Member"
--		::= { swhLLDPConfiguration 2 }
--
--	swhLLDPConfigPort3 OBJECT-TYPE
--		SYNTAX    INTEGER { b(0), v(1) }
--		ACCESS    read-write
--		STATUS    mandatory
--		DESCRIPTION
--			"b:Blocked  v:Member"
--		::= { swhLLDPConfiguration 3 }
--
--	swhLLDPConfigPort4 OBJECT-TYPE
--		SYNTAX    INTEGER { b(0), v(1) }
--		ACCESS    read-write
--		STATUS    mandatory
--		DESCRIPTION
--			"b:Blocked  v:Member"
--		::= { swhLLDPConfiguration 4 }
--
--	swhLLDPConfigPort5 OBJECT-TYPE
--		SYNTAX    INTEGER { b(0), v(1) }
--		ACCESS    read-write
--		STATUS    mandatory
--		DESCRIPTION
--			"b:Blocked  v:Member"
--		::= { swhLLDPConfiguration 5 }
--
--	swhLLDPConfigPort6 OBJECT-TYPE
--		SYNTAX    INTEGER { b(0), v(1) }
--		ACCESS    read-write
--		STATUS    mandatory
--		DESCRIPTION
--			"b:Blocked  v:Member"
--		::= { swhLLDPConfiguration 6 }
--
--
--	swhLLDPConfigReceiverHoldTime OBJECT-TYPE
--		SYNTAX    INTEGER (1..3600)
--		ACCESS    read-write
--		STATUS    mandatory
--		DESCRIPTION
--			"Receiver Hold-Time(1-3600 Secs)"
--		::= { swhLLDPConfiguration 90 }
--
--	swhLLDPConfigSendingLLDPPacketInterval OBJECT-TYPE
--		SYNTAX    INTEGER (1..180)
--		ACCESS    read-write
--		STATUS    mandatory
--		DESCRIPTION
--			"Sending LLDP Packet Interval(1-180 Secs)"
--		::= { swhLLDPConfiguration 91 }
--
--	swhLLDPConfigSendingLLDPPacketPerDiscover OBJECT-TYPE
--		SYNTAX    INTEGER (1..16)
--		ACCESS    read-write
--		STATUS    mandatory
--		DESCRIPTION
--			"Sending LLDP Packets Per Discover(1-16 Packet)"
--		::= { swhLLDPConfiguration 92 }
--
--	swhLLDPConfigItem OBJECT-TYPE
--		SYNTAX    DisplayString
--		ACCESS    read-only
--		STATUS    mandatory
--		DESCRIPTION
--			"Selection of LLDP TLVs to send"
--		::= { swhLLDPConfiguration 94 }
--
--	swhLLDPConfigPortDescription OBJECT-TYPE
--		SYNTAX    INTEGER { disable(0), enable(1) }
--		ACCESS    read-write
--		STATUS    mandatory
--		DESCRIPTION
--			"Port Description is On or Off"
--		::= { swhLLDPConfiguration 95 }
--
--	swhLLDPConfigSystemName OBJECT-TYPE
--		SYNTAX    INTEGER { disable(0), enable(1) }
--		ACCESS    read-write
--		STATUS    mandatory
--		DESCRIPTION
--			"System Name is On or Off"
--		::= { swhLLDPConfiguration 96 }
--
--	swhLLDPConfigSystemDescription OBJECT-TYPE
--		SYNTAX    INTEGER { disable(0), enable(1) }
--		ACCESS    read-write
--		STATUS    mandatory
--		DESCRIPTION
--			"System Description is On or Off"
--		::= { swhLLDPConfiguration 97 }
--
--	swhLLDPConfigSystemCapabilities OBJECT-TYPE
--		SYNTAX    INTEGER { disable(0), enable(1) }
--		ACCESS    read-write
--		STATUS    mandatory
--		DESCRIPTION
--			"System Capabilities is On or Off"
--		::= { swhLLDPConfiguration 98 }
--
--	swhLLDPConfigManagementAddress OBJECT-TYPE
--		SYNTAX    INTEGER { disable(0), enable(1) }
--		ACCESS    read-write
--		STATUS    mandatory
--		DESCRIPTION
--			"Management Address is On or Off"
--		::= { swhLLDPConfiguration 99 }


-- SwitchManagement(4).PortMirroring(15)

	swhPortMirroringEnable OBJECT-TYPE
		SYNTAX    INTEGER { disable(0), enable(1) }
		ACCESS    read-write
		STATUS    mandatory
		DESCRIPTION
			"Port Mirror disable or enable"
		::= { swhPortMirroring 53 }


-- SwitchManagement(4).PortMirroring(15).PortMirrorSourcePortConfigTable(1)

	swhPortMirrorSourcePortConfigTable OBJECT-TYPE
		SYNTAX    SEQUENCE OF SwhPortMirrorSourcePortConfigEntry
		ACCESS    not-accessible
		STATUS    mandatory
		DESCRIPTION
			"Table of Source Port Configuration."
		::= { swhPortMirroring 1 }

	-- Table Entry
	swhPortMirrorSourcePortConfigEntry OBJECT-TYPE
		SYNTAX    SwhPortMirrorSourcePortConfigEntry
		ACCESS    not-accessible
		STATUS    mandatory
		DESCRIPTION
			"An entry in the table, containing information
			about Source Port Config."
		INDEX    { swhPortMirrorSourcePortConfigIndex }
		::= { swhPortMirrorSourcePortConfigTable 1 }

	SwhPortMirrorSourcePortConfigEntry ::=
		SEQUENCE {
			swhPortMirrorSourcePortConfigIndex
				INTEGER,
			swhPortMirrorSourcePortConfigIndexID
				INTEGER,
			swhPortMirrorSourcePortConfigState
				INTEGER,
			swhPortMirrorSourcePortConfigDestinationPort
				INTEGER,
			swhPortMirrorSourcePortConfigTXPortList
				DisplayString,
			swhPortMirrorSourcePortConfigRXPortList
				DisplayString,
			swhPortMirrorSourcePortConfigDelete
				INTEGER
		}

	swhPortMirrorSourcePortConfigIndex OBJECT-TYPE
		SYNTAX    INTEGER (0..2147483647)
		ACCESS    not-accessible
		STATUS    mandatory
		DESCRIPTION
			"A unique value for each port."
		::= { swhPortMirrorSourcePortConfigEntry 1 }
		
	swhPortMirrorSourcePortConfigIndexID OBJECT-TYPE
		SYNTAX    INTEGER (1..4)
		ACCESS    read-only
		STATUS    mandatory
		DESCRIPTION
			"Index ID"
		::= { swhPortMirrorSourcePortConfigEntry 8 }

	swhPortMirrorSourcePortConfigState OBJECT-TYPE
		SYNTAX    INTEGER { disable(0), enable(1) }
		ACCESS    read-write
		STATUS    mandatory
		DESCRIPTION
			"Source Port Enable"
		::= { swhPortMirrorSourcePortConfigEntry 3 }

	swhPortMirrorSourcePortConfigDestinationPort OBJECT-TYPE
		SYNTAX    INTEGER { port01(0),
		                    port02(1),
		                    port03(2),
		                    port04(3),
		                    port05(4),
		                    port06(5)
		                    }
		ACCESS    read-write
		STATUS    mandatory
		DESCRIPTION
			"Source Port Member"
		::= { swhPortMirrorSourcePortConfigEntry 4 }

	swhPortMirrorSourcePortConfigTXPortList OBJECT-TYPE
		SYNTAX    DisplayString
		ACCESS    read-write
		STATUS    mandatory
		DESCRIPTION
			"Source Port TX Port List"
		::= { swhPortMirrorSourcePortConfigEntry 5 }

	swhPortMirrorSourcePortConfigRXPortList OBJECT-TYPE
		SYNTAX    DisplayString
		ACCESS    read-write
		STATUS    mandatory
		DESCRIPTION
			"Source Port RX Port List"
		::= { swhPortMirrorSourcePortConfigEntry 6 }
		
	swhPortMirrorSourcePortConfigDelete OBJECT-TYPE
		SYNTAX    INTEGER { normal(0), delete(1) }
		ACCESS    read-write
		STATUS    mandatory
		DESCRIPTION
			"Delete this entry."
		::= { swhPortMirrorSourcePortConfigEntry 7 }


-- SwitchManagement(4).StormControl(16)


-- SwitchManagement(4).MirroringConfiguration(17)


-- SwitchManagement(4).MirroringConfiguration(17).MirrorSourcePortConfigTable(10)


-- SwitchManagement(4).MirroringConfiguration(17).MirrorVIDConfigTable(11)


-- SwitchManagement(4).MirroringConfiguration(17).MirrorDestinationIPConfigTable(12)


-- SwitchManagement(4).MirroringConfiguration(17).MirrorSourceIPConfigTable(13)


-- SwitchManagement(4).DIDOConfiguration(22).DIConfigTable(1)
--
--	swhDIConfigTable OBJECT-TYPE
--		SYNTAX    SEQUENCE OF SwhDIConfigEntry
--		ACCESS    not-accessible
--		STATUS    mandatory
--		DESCRIPTION
--			"Table of digital input config."
--		::= { swhDIConfiguration 1 }
--
	-- Table Entry
--	swhDIConfigEntry OBJECT-TYPE
--		SYNTAX    SwhDIConfigEntry
--		ACCESS    not-accessible
--		STATUS    mandatory
--		DESCRIPTION
--			"An entry in the table, containing information
--			about digital input config."
--		INDEX    { swhDIConfigIndex }
--		::= { swhDIConfigTable 1 }
--
--	SwhDIConfigEntry ::=
--		SEQUENCE {
--			swhDIConfigIndex
--				INTEGER,
--			swhDIConfigNormal
--				INTEGER
--		}
--
--	swhDIConfigIndex OBJECT-TYPE
--		SYNTAX    INTEGER (0..2147483647)
--		ACCESS    not-accessible
--		STATUS    mandatory
--		DESCRIPTION
--			"A unique value for each digital input."
--		::= { swhDIConfigEntry 1 }
--
--	swhDIConfigNormal OBJECT-TYPE
--		SYNTAX    INTEGER { close(0), open(1) }
--		ACCESS    read-write
--		STATUS    mandatory
--		DESCRIPTION
--			"digital input normal."
--		::= { swhDIConfigEntry 2 }


-- SwitchManagement(4).DIDOConfiguration(22).DOConfigTable(2)


-- SwitchManagement(4).POEConfiguration(23)


-- SwitchManagement(4).RingDetection(24)

--	swhRingDetectionEnable OBJECT-TYPE
--		SYNTAX    INTEGER { disable(0), enable(1) }
--		ACCESS    read-write
--		STATUS    mandatory
--		DESCRIPTION
--			"Specify Ring Detection Enable"
--		::= { swhRingDetection 1 }

--	swhRingDetectionAccording OBJECT-TYPE
--		SYNTAX    INTEGER { software(0), hardware(1) }
--		ACCESS    read-write
--		STATUS    mandatory
--		DESCRIPTION
--			"Specify Ring Detection According"
--		::= { swhRingDetection 3 }

--	swhRingDetectionSoftwareRole OBJECT-TYPE
--		SYNTAX    INTEGER { slave(0), master(1) }
--		ACCESS    read-write
--		STATUS    mandatory
--		DESCRIPTION
--			"Specify Ring Detection Software Role"
--		::= { swhRingDetection 2 }

--	swhRingDetectionPortList OBJECT-TYPE
--		SYNTAX    DisplayString
--		ACCESS    read-write
--		STATUS    mandatory
--		DESCRIPTION
--			"Specify Ring Detection Port List"
--		::= { swhRingDetection 4 }


-- SwitchManagement(4).QoSPriority(30)


-- SwitchManagement(4).QoSPriority(30).PortPriorityTable(4)


-- SwitchManagement(4).QoSPriority(30).8021pPriorityTable(5)


-- SwitchManagement(4).QoSPriority(30).DSCPPriorityTable(6)


-- SwitchManagement(4).QoSPriority(30).VLANPriorityTable(25)


-- SwitchManagement(4).QoSPriority(30).8021pRemarkingTable(31)


-- SwitchManagement(4).QoSPriority(30).8021pRemarkingDSCPTable(32)


-- SwitchManagement(4).QoSPriority(30).DSCPRemarkingTable(41)


-- SwitchManagement(4).QoSPriority(30).DSCPPortRemarkingTable(42)


-- SwitchManagement(4).QoSPriority(30).VIDRemarkingTable(51)


-- SwitchManagement(4).MacAddressManagement(35)

	swhMACTableLearning
		OBJECT IDENTIFIER ::= { swhMacAddressManagement 1 }
	swhStaticMACTableConfiguration
		OBJECT IDENTIFIER ::= { swhMacAddressManagement 3 }


-- SwitchManagement(4).MacAddressManagement(35).MACTableLearning(1).MACTableLearningTable(2)

	swhMACTableLearningTable OBJECT-TYPE
		SYNTAX    SEQUENCE OF SwhMACTableLearningEntry
		ACCESS    not-accessible
		STATUS    mandatory
		DESCRIPTION
			"Table of MAC Table Learning."
		::= { swhMACTableLearning 2 }

	-- Table Entry
	swhMACTableLearningEntry OBJECT-TYPE
		SYNTAX    SwhMACTableLearningEntry
		ACCESS    not-accessible
		STATUS    mandatory
		DESCRIPTION
			"An entry in the table, containing information
			about MAC Table Learnin."
		INDEX    { swhMACTableLearningIndex }
		::= { swhMACTableLearningTable 1 }

	SwhMACTableLearningEntry ::=
		SEQUENCE {
			swhMACTableLearningIndex
				INTEGER,
			swhMACTableLearningLearning
				INTEGER
		}

	swhMACTableLearningIndex OBJECT-TYPE
		SYNTAX    INTEGER (0..2147483647)
		ACCESS    not-accessible
		STATUS    mandatory
		DESCRIPTION
			"A unique value for each MAC Table Learnin."
		::= { swhMACTableLearningEntry 1 }

	swhMACTableLearningLearning OBJECT-TYPE
		SYNTAX    INTEGER { auto(0), disable(1) }
		ACCESS    read-write
		STATUS    mandatory
		DESCRIPTION
			"Learning."
		::= { swhMACTableLearningEntry 2 }


-- SwitchManagement(4).MacAddressManagement(35).StaticMACTableConfiguration(3)

--	swhStaticMACTablePort OBJECT-TYPE
--		SYNTAX    INTEGER { port01(0),
--		                    port02(1),
--		                    port03(2),
--		                    port04(3),
--		                    port05(4),
--		                    port06(5)
--		                    }
--		ACCESS    read-write
--		STATUS    mandatory
--		DESCRIPTION
--			"Per port search static MAC table."
--		::= { swhStaticMACTableConfiguration 1 }


-- SwitchManagement(4).MacAddressManagement(35).StaticMACTableConfiguration(3).StaticForwardTable(2)

	swhStaticForwardTable OBJECT-TYPE
		SYNTAX    SEQUENCE OF SwhStaticForwardEntry
		ACCESS    not-accessible
		STATUS    mandatory
		DESCRIPTION
			"Table of Static Forwarding."
		::= { swhStaticMACTableConfiguration 2 }

	-- Table Entry
	swhStaticForwardEntry OBJECT-TYPE
		SYNTAX    SwhStaticForwardEntry
		ACCESS    not-accessible
		STATUS    mandatory
		DESCRIPTION
			"An entry in the table, containing information
			about Static Forwarding Configuration"
		INDEX    { swhStaticForwardIndex }
		::= { swhStaticForwardTable 1 }

	SwhStaticForwardEntry ::=
		SEQUENCE {
			swhStaticForwardIndex
				INTEGER,  
			swhStaticForwardValid
				INTEGER,  
			swhStaticForwardMacAddress
				MacAddress, 
			swhStaticForwardVID
				INTEGER,
			swhStaticForwardPort
				INTEGER,
--			swhStaticForwardType
--				DisplayString,
--			swhStaticForwardAddtoStatic
--				INTEGER,
			swhStaticForwardDelete
				INTEGER
		}

	swhStaticForwardIndex OBJECT-TYPE
		SYNTAX    INTEGER (0..2147483647)
		ACCESS    not-accessible
		STATUS    mandatory
		DESCRIPTION
			"A unique value for Static Forwarding index."
		::= { swhStaticForwardEntry 1 }

	swhStaticForwardValid OBJECT-TYPE
		SYNTAX    INTEGER { invalid(0), valid(1) }
		ACCESS    read-only
		STATUS    mandatory
		DESCRIPTION
			"This MAC address is valid or invalid."
		::= { swhStaticForwardEntry 2 }

	swhStaticForwardMacAddress OBJECT-TYPE
		SYNTAX    MacAddress
		ACCESS    read-write
		STATUS    mandatory
		DESCRIPTION
			"MAC Address"
		::= { swhStaticForwardEntry 3 }

	swhStaticForwardVID OBJECT-TYPE
		SYNTAX    INTEGER (1..4094)
		ACCESS    read-write
		STATUS    mandatory
		DESCRIPTION
			"VLAN ID"
		::= { swhStaticForwardEntry 4 }

	swhStaticForwardPort OBJECT-TYPE
		SYNTAX    INTEGER { port01(0),
		                    port02(1),
		                    port03(2),
		                    port04(3),
		                    port05(4),
		                    port06(5)
		                    }
		ACCESS    read-write
		STATUS    mandatory
		DESCRIPTION
			"Static forward packets to this port."
		::= { swhStaticForwardEntry 5 }

	swhStaticForwardDelete OBJECT-TYPE
		SYNTAX    INTEGER { normal(0), delete(1) }
		ACCESS    read-write
		STATUS    mandatory
		DESCRIPTION
			"Delete this MAC address."
		::= { swhStaticForwardEntry 6 }

--	swhStaticForwardType OBJECT-TYPE
--		SYNTAX    DisplayString
--		ACCESS    read-only
--		STATUS    mandatory
--		DESCRIPTION
--			"Type is Manual or Sticky"
--		::= { swhStaticForwardEntry 7 }

--	swhStaticForwardAddtoStatic OBJECT-TYPE
--		SYNTAX    INTEGER { normal(0), add(1) }
--		ACCESS    read-write
--		STATUS    mandatory
--		DESCRIPTION
--			"Add Sticky to Static."
--		::= { swhStaticForwardEntry 8 }


-- SwitchManagement(4).Layer2ProtocolTunnel(37)
--
--	swhL2PTConfigState OBJECT-TYPE
--		SYNTAX    INTEGER { disable(0), enable(1) }
--		ACCESS    read-write
--		STATUS    mandatory
--		DESCRIPTION
--			"Layer 2 Protocol Tunneling is Disable or Enable"
--		::= { swhLayer2ProtocolTunnel 1 }
--
--	swhL2PTConfigDestinationMACAddress OBJECT-TYPE
--		SYNTAX    DisplayString (SIZE (0..256))
--		ACCESS    read-write
--		STATUS    mandatory
--		DESCRIPTION
--			"Destination MAC Address"
--		::= { swhLayer2ProtocolTunnel 2 }
--
--	swhL2PTConfigClassOfService OBJECT-TYPE
--		SYNTAX    INTEGER (0..7)
--		ACCESS    read-write
--		STATUS    mandatory
--		DESCRIPTION
--			"Class of Service(0-7)"
--		::= { swhLayer2ProtocolTunnel 3 }
--
-- SwitchManagement(4).Layer2ProtocolTunnel(37).L2PTPortConfigTable(5)
--
--	swhL2PTPortConfigTable OBJECT-TYPE
--		SYNTAX    SEQUENCE OF SwhL2PTPortConfigEntry
--		ACCESS    not-accessible
--		STATUS    mandatory
--		DESCRIPTION
--			"Table of Layer 2 Protocol Tunneling."
--		::= { swhLayer2ProtocolTunnel 5 }
--
	-- Table Entry
--	swhL2PTPortConfigEntry OBJECT-TYPE
--		SYNTAX    SwhL2PTPortConfigEntry
--		ACCESS    not-accessible
--		STATUS    mandatory
--		DESCRIPTION
--			"An entry in the table, containing information
--			about Layer 2 Protocol Tunneling Configuration"
--		INDEX    { swhL2PTPortConfigIndex }
--		::= { swhL2PTPortConfigTable 1 }
--
--	SwhL2PTPortConfigEntry ::=
--		SEQUENCE {
--			swhL2PTPortConfigIndex
--				INTEGER,
--			swhL2PTPortConfigPort
--				DisplayString,
--			swhL2PTPortConfigCDP
--				INTEGER, 
--			swhL2PTPortConfigLLDP
--				INTEGER,
--			swhL2PTPortConfigSTP
--				INTEGER,
--			swhL2PTPortConfigVTP
--				INTEGER,
--			swhL2PTPortConfigLACP
--				INTEGER,
--			swhL2PTPortConfigPAgP
--				INTEGER,
--			swhL2PTPortConfigUDLD
--				INTEGER,
--			swhL2PTPortConfigClear
--				INTEGER
--		}
--
--	swhL2PTPortConfigIndex OBJECT-TYPE
--		SYNTAX    INTEGER (0..2147483647)
--		ACCESS    not-accessible
--		STATUS    mandatory
--		DESCRIPTION
--			"A unique value for Layer 2 Protocol Tunneling index."
--		::= { swhL2PTPortConfigEntry 1 }
--
--	swhL2PTPortConfigPort OBJECT-TYPE
--		SYNTAX    DisplayString
--		ACCESS    read-only
--		STATUS    mandatory
--		DESCRIPTION
--			"Layer 2 Protocol Tunneling Port Number."
--		::= { swhL2PTPortConfigEntry 2 }
--
--	swhL2PTPortConfigCDP OBJECT-TYPE
--		SYNTAX    INTEGER { b(0), v(1) }
--		ACCESS    read-write
--		STATUS    mandatory
--		DESCRIPTION
--			"CDP."
--		::= { swhL2PTPortConfigEntry 3 }
--
--	swhL2PTPortConfigLLDP OBJECT-TYPE
--		SYNTAX    INTEGER { b(0), v(1) }
--		ACCESS    read-write
--		STATUS    mandatory
--		DESCRIPTION
--			"LLDP."
--		::= { swhL2PTPortConfigEntry 4 }
--
--	swhL2PTPortConfigSTP OBJECT-TYPE
--		SYNTAX    INTEGER { b(0), v(1) }
--		ACCESS    read-write
--		STATUS    mandatory
--		DESCRIPTION
--			"STP."
--		::= { swhL2PTPortConfigEntry 5 }
--
--	swhL2PTPortConfigVTP OBJECT-TYPE
--		SYNTAX    INTEGER { b(0), v(1) }
--		ACCESS    read-write
--		STATUS    mandatory
--		DESCRIPTION
--			"VTP."
--		::= { swhL2PTPortConfigEntry 6 }
--
--	swhL2PTPortConfigLACP OBJECT-TYPE
--		SYNTAX    INTEGER { b(0), v(1) }
--		ACCESS    read-write
--		STATUS    mandatory
--		DESCRIPTION
--			"LACP."
--		::= { swhL2PTPortConfigEntry 7 }
--
--	swhL2PTPortConfigPAgP OBJECT-TYPE
--		SYNTAX    INTEGER { b(0), v(1) }
--		ACCESS    read-write
--		STATUS    mandatory
--		DESCRIPTION
--			"PAgP."
--		::= { swhL2PTPortConfigEntry 8 }
--
--	swhL2PTPortConfigUDLD OBJECT-TYPE
--		SYNTAX    INTEGER { b(0), v(1) }
--		ACCESS    read-write
--		STATUS    mandatory
--		DESCRIPTION
--			"UDLD."
--		::= { swhL2PTPortConfigEntry 9 }
--
--	swhL2PTPortConfigClear OBJECT-TYPE
--		SYNTAX    INTEGER { normal(0), clear(1) }
--		ACCESS    read-write
--		STATUS    mandatory
--		DESCRIPTION
--			"Clear this port setting."
--		::= { swhL2PTPortConfigEntry 50 }


-- SwitchManagement(4).RapidSpanningTree(40)

--	swhSTPSwitchSettings
--		OBJECT IDENTIFIER ::= { swhSpanningTree 3 }
--	swhSTPAggregatedPortSettings
--		OBJECT IDENTIFIER ::= { swhSpanningTree 9 }
--	swhSTPPhysicalPortSettings
--		OBJECT IDENTIFIER ::= { swhSpanningTree 12 }
--	swhMSTInstance
--		OBJECT IDENTIFIER ::= { swhSpanningTree 15 }
--	swhMSTPPhysicalPortSettings
--		OBJECT IDENTIFIER ::= { swhSpanningTree 18 }
--
--
-- SwitchManagement(4).RapidSpanningTree(40).RSTPSwitchSettings(3)
--
--	swhSTPSwitchSettingsEnable OBJECT-TYPE
--		SYNTAX    INTEGER { disable(0), enable(1) }
--		ACCESS    read-write
--		STATUS    mandatory
--		DESCRIPTION
--			"RSTP Switch State is Disable or Enable"
--		::= { swhSTPSwitchSettings 22 }
--
--	swhSTPSwitchSettingsSystemPriority OBJECT-TYPE
--		SYNTAX    INTEGER (0..2147483647)
--		ACCESS    read-only
--		STATUS    mandatory
--		DESCRIPTION
--			"System Priority"
--		::= { swhSTPSwitchSettings 6 }
--
--	swhSTPSwitchSettingsSystemPriorityIndex OBJECT-TYPE
--		SYNTAX    INTEGER { priority-0(0),
--		                    priority-4096(1),
--		                    priority-8192(2),
--		                    priority-12288(3),
--		                    priority-16384(4),
--		                    priority-20480(5),
--		                    priority-24576(6),
--		                    priority-28672(7),
--		                    priority-32768(8),
--		                    priority-36864(9),
--		                    priority-40960(10),
--		                    priority-45056(11),
--		                    priority-49152(12),
--		                    priority-53248(13),
--		                    priority-57344(14),
--		                    priority-61440(15)
--		                    }
--		ACCESS    read-write
--		STATUS    mandatory
--		DESCRIPTION
--			"Port Priority"
--		::= { swhSTPSwitchSettings 9 }
--
--	swhSTPSwitchSettingsMaxAge OBJECT-TYPE
--		SYNTAX    INTEGER (6..200)
--		ACCESS    read-write
--		STATUS    mandatory
--		DESCRIPTION
--			"Max Age is 6-40 hops"
--		::= { swhSTPSwitchSettings 12 }
--
--	swhSTPSwitchSettingsHelloTime OBJECT-TYPE
--		SYNTAX    INTEGER (1..10)
--		ACCESS    read-write
--		STATUS    mandatory
--		DESCRIPTION
--			"Hello Time is 1-10 secs"
--		::= { swhSTPSwitchSettings 15 }
--
--	swhSTPSwitchSettingsForwardDelay OBJECT-TYPE
--		SYNTAX    INTEGER (4..30)
--		ACCESS    read-write
--		STATUS    mandatory
--		DESCRIPTION
--			"Forward Delay is 4-30 secs"
--		::= { swhSTPSwitchSettings 18 }
--
--	swhSTPSwitchSettingsForceVersion OBJECT-TYPE
--		SYNTAX    INTEGER { stp(0), rstp(1), mstp(2) }
--		ACCESS    read-write
--		STATUS    mandatory
--		DESCRIPTION
--			"Force Version is Normal or Compatible"
--		::= { swhSTPSwitchSettings 21 }
--
--	swhSTPSwitchSettingsRegionName OBJECT-TYPE
--		SYNTAX    DisplayString (SIZE (0..255))
--		ACCESS    read-write
--		STATUS    mandatory
--		DESCRIPTION
--			"Region Name"
--		::= { swhSTPSwitchSettings 23 }
--
--	swhSTPSwitchSettingsRevision OBJECT-TYPE
--		SYNTAX    INTEGER (0..65535)
--		ACCESS    read-write
--		STATUS    mandatory
--		DESCRIPTION
--			"Revision"
--		::= { swhSTPSwitchSettings 24 }
--
--	swhSTPSwitchSettingsMaxHop OBJECT-TYPE
--		SYNTAX    INTEGER (1..40)
--		ACCESS    read-write
--		STATUS    mandatory
--		DESCRIPTION
--			"Max Hop"
--		::= { swhSTPSwitchSettings 25 }
--
--
-- SwitchManagement(4).RapidSpanningTree(40).RSTPAggregatedPortSettings(9)
--
--	swhSTPAggregatedPortSettingsState OBJECT-TYPE
--		SYNTAX    INTEGER { disable(0), enable(1) }
--		ACCESS    read-write
--		STATUS    mandatory
--		DESCRIPTION
--			"Aggregated State is Disable or Enable"
--		::= { swhSTPAggregatedPortSettings 3 }
--
--	swhSTPAggregatedPortSettingsCost OBJECT-TYPE
--		SYNTAX    INTEGER (1..200000000)
--		ACCESS    read-write
--		STATUS    mandatory
--		DESCRIPTION
--			"Aggregated State is Disable or Enable"
--		::= { swhSTPAggregatedPortSettings 6 }
--
--	swhSTPAggregatedPortSettingsPriority OBJECT-TYPE
--		SYNTAX    INTEGER (0..2147483647)
--		ACCESS    read-only
--		STATUS    mandatory
--		DESCRIPTION
--			"Aggregated State is Disable or Enable"
--		::= { swhSTPAggregatedPortSettings 9 }
--
--	swhSTPAggregatedPortSettingsPriorityIndex OBJECT-TYPE
--		SYNTAX    INTEGER { priority-0(0),
--		                    priority-16(1),
--		                    priority-32(2),
--		                    priority-48(3),
--		                    priority-64(4),
--		                    priority-80(5),
--		                    priority-96(6),
--		                    priority-112(7),
--		                    priority-128(8),
--		                    priority-144(9),
--		                    priority-160(10),
--		                    priority-176(11),
--		                    priority-192(12),
--		                    priority-208(13),
--		                    priority-224(14),
--		                    priority-240(15)
--		                    }
--		ACCESS    read-write
--		STATUS    mandatory
--		DESCRIPTION
--			"Port Priority"
--		::= { swhSTPAggregatedPortSettings 12 }
--
--	swhSTPAggregatedPortSettingsEdge OBJECT-TYPE
--		SYNTAX    INTEGER { disable(0), enable(1) }
--		ACCESS    read-write
--		STATUS    mandatory
--		DESCRIPTION
--			"Edge Enable"
--		::= { swhSTPAggregatedPortSettings 15 }
--
--	swhSTPAggregatedPortSettingsPoint2point OBJECT-TYPE
--		SYNTAX    INTEGER { forcedtrue(0), forcedfalse(1), auto(2) }
--		ACCESS    read-write
--		STATUS    mandatory
--		DESCRIPTION
--			"Point to Point"
--		::= { swhSTPAggregatedPortSettings 18 }
--
--
-- SwitchManagement(4).RapidSpanningTree(40).RSTPPhysicalPortSettings(12).RSTPPhysicalPortSettingsTable(3)
--
--	swhSTPPhysicalPortSettingsTable OBJECT-TYPE
--		SYNTAX    SEQUENCE OF SwhSTPPhysicalPortSettingsEntry
--		ACCESS    not-accessible
--		STATUS    mandatory
--		DESCRIPTION
--			"Table of RSTP Physical Port descriptive and status information."
--		::= { swhSTPPhysicalPortSettings 3 }
--
	-- Table Entry
--	swhSTPPhysicalPortSettingsEntry OBJECT-TYPE
--		SYNTAX    SwhSTPPhysicalPortSettingsEntry
--		ACCESS    not-accessible
--		STATUS    mandatory
--		DESCRIPTION
--			"An entry in the table, containing information
--			about RSTP Physical Port Settings."
--		INDEX    { swhSTPPhysicalPortSettingsIndex }
--		::= { swhSTPPhysicalPortSettingsTable 1 }
--
--	SwhSTPPhysicalPortSettingsEntry ::=
--		SEQUENCE {  
--			swhSTPPhysicalPortSettingsIndex
--				INTEGER,
--			swhSTPPhysicalPortSettingsState
--				INTEGER,
--			swhSTPPhysicalPortSettingsPathCost
--				INTEGER,
--			swhSTPPhysicalPortSettingsPriority
--				INTEGER,
--			swhSTPPhysicalPortSettingsPriorityIndex
--				INTEGER,
--			swhSTPPhysicalPortSettingsEdge
--				INTEGER,
--			swhSTPPhysicalPortSettingsPoint2point
--				INTEGER
--		}
--
--	swhSTPPhysicalPortSettingsIndex OBJECT-TYPE
--		SYNTAX    INTEGER (0..2147483647)
--		ACCESS    not-accessible
--		STATUS    mandatory
--		DESCRIPTION
--			"A unique value for each port."
--		::= { swhSTPPhysicalPortSettingsEntry 3 }
--
--	swhSTPPhysicalPortSettingsState OBJECT-TYPE
--		SYNTAX    INTEGER { disable(0), enable(1) }
--		ACCESS    read-write
--		STATUS    mandatory
--		DESCRIPTION
--			"Port Protocol Enable"
--		::= { swhSTPPhysicalPortSettingsEntry 6 }
--
--	swhSTPPhysicalPortSettingsEdge OBJECT-TYPE
--		SYNTAX    INTEGER { disable(0), enable(1) }
--		ACCESS    read-write
--		STATUS    mandatory
--		DESCRIPTION
--			"Edge Enable"
--		::= { swhSTPPhysicalPortSettingsEntry 9 }
--
--	swhSTPPhysicalPortSettingsPathCost OBJECT-TYPE
--		SYNTAX    INTEGER (0..200000000)
--		ACCESS    read-write
--		STATUS    mandatory
--		DESCRIPTION
--			"Path Cost is 0-200000000"
--		::= { swhSTPPhysicalPortSettingsEntry 12 }
--
--	swhSTPPhysicalPortSettingsPriority OBJECT-TYPE
--		SYNTAX    INTEGER (0..2147483647)
--		ACCESS    read-only
--		STATUS    mandatory
--		DESCRIPTION
--			"Priority."
--		::= { swhSTPPhysicalPortSettingsEntry 15 }
--
--	swhSTPPhysicalPortSettingsPriorityIndex OBJECT-TYPE
--		SYNTAX    INTEGER { priority-0(0),
--		                    priority-16(1),
--		                    priority-32(2),
--		                    priority-48(3),
--		                    priority-64(4),
--		                    priority-80(5),
--		                    priority-96(6),
--		                    priority-112(7),
--		                    priority-128(8),
--		                    priority-144(9),
--		                    priority-160(10),
--		                    priority-176(11),
--		                    priority-192(12),
--		                    priority-208(13),
--		                    priority-224(14),
--		                    priority-240(15)
--		                    }
--		ACCESS    read-write
--		STATUS    mandatory
--		DESCRIPTION
--			"Port Priority"
--		::= { swhSTPPhysicalPortSettingsEntry 18 }
--
--	swhSTPPhysicalPortSettingsPoint2point OBJECT-TYPE
--		SYNTAX    INTEGER { forcedtrue(0), forcedfalse(1), auto(2) }
--		ACCESS    read-write
--		STATUS    mandatory
--		DESCRIPTION
--			"Point to Point"
--		::= { swhSTPPhysicalPortSettingsEntry 21 }
--
--
-- SwitchManagement(4).RapidSpanningTree(40).MSTInstance(15)
--
--	swhMSTInstanceTable OBJECT-TYPE
--		SYNTAX    SEQUENCE OF SwhMSTInstanceEntry
--		ACCESS    not-accessible
--		STATUS    mandatory
--		DESCRIPTION
--			"Table of Static Forwarding."
--		::= { swhMSTInstance 3 }
--
	-- Table Entry
--	swhMSTInstanceEntry OBJECT-TYPE
--		SYNTAX    SwhMSTInstanceEntry
--		ACCESS    not-accessible
--		STATUS    mandatory
--		DESCRIPTION
--			"An entry in the table, containing information
--			about Static Forwarding Configuration"
--		INDEX    { swhMSTInstanceIndex }
--		::= { swhMSTInstanceTable 1 }
--
--	SwhMSTInstanceEntry ::=
--		SEQUENCE {
--			swhMSTInstanceIndex
--				INTEGER,
--			swhMSTInstanceMSTI
--				DisplayString,
--			swhMSTInstancePriority
--				INTEGER,
--			swhMSTInstanceVLAN
--				DisplayString
--		}
--
--	swhMSTInstanceIndex OBJECT-TYPE
--		SYNTAX    INTEGER (0..2147483647)
--		ACCESS    not-accessible
--		STATUS    mandatory
--		DESCRIPTION
--			"A unique value for MST Instance index."
--		::= { swhMSTInstanceEntry 1 }
--
--	swhMSTInstanceMSTI OBJECT-TYPE
--		SYNTAX    DisplayString
--		ACCESS    read-only
--		STATUS    mandatory
--		DESCRIPTION
--			"Port Settings packets to this port."
--		::= { swhMSTInstanceEntry 2 }
--
--	swhMSTInstancePriority OBJECT-TYPE
--		SYNTAX    INTEGER { priority-0(0),
--		                    priority-4096(1),
--		                    priority-8192(2),
--		                    priority-12288(3),
--		                    priority-16384(4),
--		                    priority-20480(5),
--		                    priority-24576(6),
--		                    priority-28672(7),
--		                    priority-32768(8),
--		                    priority-36864(9),
--		                    priority-40960(10),
--		                    priority-45056(11),
--		                    priority-49152(12),
--		                    priority-53248(13),
--		                    priority-57344(14),
--		                    priority-61440(15)
--		                    }
--		ACCESS    read-write
--		STATUS    mandatory
--		DESCRIPTION
--			"Priority"
--		::= { swhMSTInstanceEntry 3 }
--
--	swhMSTInstanceVLAN OBJECT-TYPE
--		SYNTAX    DisplayString
--		ACCESS    read-write
--		STATUS    mandatory
--		DESCRIPTION
--			"VLAN List"
--		::= { swhMSTInstanceEntry 4 }
--
--
-- SwitchManagement(4).RapidSpanningTree(40).MSTPPhysicalPortSettings(18)
--
--	swhPortSettingsMSTI OBJECT-TYPE
--		SYNTAX    INTEGER { MSTI00(0),
--		                    MSTI01(1),
--		                    MSTI02(2),
--		                    MSTI03(3),
--		                    MSTI04(4),
--		                    MSTI05(5),
--		                    MSTI06(6),
--		                    MSTI07(7),
--		                    MSTI08(8),
--		                    MSTI09(9),
--		                    MSTI10(10),
--		                    MSTI11(11),
--		                    MSTI12(12),
--		                    MSTI13(13),
--		                    MSTI14(14),
--		                    MSTI15(15)
--		                    }
--		ACCESS    read-write
--		STATUS    mandatory
--		DESCRIPTION
--			"MSTI."
--		::= { swhMSTPPhysicalPortSettings 1 }
--
--
-- SwitchManagement(4).RapidSpanningTree(40).MSTPPhysicalPortSettings(15).MSTPPhysicalPortSettingsTable(3)
--
--	swhMSTPPhysicalPortSettingsTable OBJECT-TYPE
--		SYNTAX    SEQUENCE OF SwhPortSettingsEntry
--		ACCESS    not-accessible
--		STATUS    mandatory
--		DESCRIPTION
--			"Table of Static Forwarding."
--		::= { swhMSTPPhysicalPortSettings 2 }
--
	-- Table Entry
--	swhPortSettingsEntry OBJECT-TYPE
--		SYNTAX    SwhPortSettingsEntry
--		ACCESS    not-accessible
--		STATUS    mandatory
--		DESCRIPTION
--			"An entry in the table, containing information
--			about Static Forwarding Configuration"
--		INDEX    { swhPortSettingsIndex }
--		::= { swhMSTPPhysicalPortSettingsTable 1 }
--
--	SwhPortSettingsEntry ::=
--		SEQUENCE {
--			swhPortSettingsIndex
--				INTEGER,
--			swhPortSettingsPort
--				DisplayString,
--			swhPortSettingsPathCost
--				INTEGER,
--			swhPortSettingsPriority
--				INTEGER
--		}
--
--	swhPortSettingsIndex OBJECT-TYPE
--		SYNTAX    INTEGER (0..2147483647)
--		ACCESS    not-accessible
--		STATUS    mandatory
--		DESCRIPTION
--			"A unique value for Port Settings index."
--		::= { swhPortSettingsEntry 1 }
--
--	swhPortSettingsPort OBJECT-TYPE
--		SYNTAX    DisplayString
--		ACCESS    read-only
--		STATUS    mandatory
--		DESCRIPTION
--			"Port Settings packets to this port."
--		::= { swhPortSettingsEntry 2 }
--
--	swhPortSettingsPathCost OBJECT-TYPE
--		SYNTAX    INTEGER (1..4094)
--		ACCESS    read-write
--		STATUS    mandatory
--		DESCRIPTION
--			"Path Cost"
--		::= { swhPortSettingsEntry 3 }
--
--	swhPortSettingsPriority OBJECT-TYPE
--		SYNTAX    INTEGER { priority-0(0),
--		                    priority-16(1),
--		                    priority-32(2),
--		                    priority-48(3),
--		                    priority-64(4),
--		                    priority-80(5),
--		                    priority-96(6),
--		                    priority-112(7),
--		                    priority-128(8),
--		                    priority-144(9),
--		                    priority-160(10),
--		                    priority-176(11),
--		                    priority-192(12),
--		                    priority-208(13),
--		                    priority-224(14),
--		                    priority-240(15)
--		                    }
--		ACCESS    read-write
--		STATUS    mandatory
--		DESCRIPTION
--			"Port Priority"
--		::= { swhPortSettingsEntry 4 }


-- SwitchManagement(4).LinkAggregation(45)

--	swhDistributionRule
--		OBJECT IDENTIFIER ::= { swhLinkAggregation 1 }
--	swhPortTrunkConfiguration
--		OBJECT IDENTIFIER ::= { swhLinkAggregation 3 }
--	swhLACPPortConfiguration
--		OBJECT IDENTIFIER ::= { swhLinkAggregation 6 }
--
--
-- SwitchManagement(4).LinkAggregation(45).DistributionRule(1)
--
--	swhDistributionRuleSourceMACAddress OBJECT-TYPE
--		SYNTAX    INTEGER { disable(0), enable(1) }
--		ACCESS    read-write
--		STATUS    mandatory
--		DESCRIPTION
--			"Source MAC Address."
--		::= { swhDistributionRule 5 }
--
--	swhDistributionRuleDestinationMACAddress OBJECT-TYPE
--		SYNTAX    INTEGER { disable(0), enable(1) }
--		ACCESS    read-write
--		STATUS    mandatory
--		DESCRIPTION
--			"Destination MAC Address."
--		::= { swhDistributionRule 6 }
--
--	swhDistributionRuleSourceIPAddress OBJECT-TYPE
--		SYNTAX    INTEGER { disable(0), enable(1) }
--		ACCESS    read-write
--		STATUS    mandatory
--		DESCRIPTION
--			"Source IP Address."
--		::= { swhDistributionRule 1 }
--
--	swhDistributionRuleDestinationIPAddress OBJECT-TYPE
--		SYNTAX    INTEGER { disable(0), enable(1) }
--		ACCESS    read-write
--		STATUS    mandatory
--		DESCRIPTION
--			"Destination IP Address."
--		::= { swhDistributionRule 2 }
--
--	swhDistributionRuleSourceL4Port OBJECT-TYPE
--		SYNTAX    INTEGER { disable(0), enable(1) }
--		ACCESS    read-write
--		STATUS    mandatory
--		DESCRIPTION
--			"Source L4 Port."
--		::= { swhDistributionRule 3 }
--
--	swhDistributionRuleDestinationL4Port OBJECT-TYPE
--		SYNTAX    INTEGER { disable(0), enable(1) }
--		ACCESS    read-write
--		STATUS    mandatory
--		DESCRIPTION
--			"Destination L4 Port."
--		::= { swhDistributionRule 4 }
--
--
-- SwitchManagement(4).LinkAggregation(45).PortTrunkConfiguration(3).PortTrunkConfigTable(6)
--
--	swhPortTrunkConfigTable OBJECT-TYPE
--		SYNTAX    SEQUENCE OF SwhPortTrunkConfigEntry
--		ACCESS    not-accessible
--		STATUS    mandatory
--		DESCRIPTION
--			"Table of Port Trunk Configuration."
--		::= { swhPortTrunkConfiguration 6 }
--
	-- Table Entry
--	swhPortTrunkConfigEntry OBJECT-TYPE
--		SYNTAX    SwhPortTrunkConfigEntry
--		ACCESS    not-accessible
--		STATUS    mandatory
--		DESCRIPTION
--			"An entry in the table, containing information
--			about port trunk config."
--		INDEX    { swhPortTrunkConfigIndex }
--		::= { swhPortTrunkConfigTable 1 }
--
--	SwhPortTrunkConfigEntry ::=
--		SEQUENCE {
--			swhPortTrunkConfigIndex
--				INTEGER,
--			swhPortTrunkConfigValid
--				INTEGER,
--			swhPortTrunkConfigGroupName
--				DisplayString,
--			swhPortTrunkConfigPort1
--				INTEGER,
--			swhPortTrunkConfigPort2
--				INTEGER,
--			swhPortTrunkConfigPort3
--				INTEGER,
--			swhPortTrunkConfigPort4
--				INTEGER,
--			swhPortTrunkConfigPort5
--				INTEGER,
--			swhPortTrunkConfigPort6
--				INTEGER,
--			swhPortTrunkConfigDelete
--				INTEGER
--		}
--
--	swhPortTrunkConfigIndex OBJECT-TYPE
--		SYNTAX    INTEGER (0..2147483647)
--		ACCESS    not-accessible
--		STATUS    mandatory
--		DESCRIPTION
--			"A unique value for each group."
--		::= { swhPortTrunkConfigEntry 1 }
--
--	swhPortTrunkConfigValid OBJECT-TYPE
--		SYNTAX    INTEGER { invalid(0), valid(1) }
--		ACCESS    read-only
--		STATUS    mandatory
--		DESCRIPTION
--			"This group setting is valid or invalid."
--		::= { swhPortTrunkConfigEntry 2 }
--
--	swhPortTrunkConfigGroupName OBJECT-TYPE
--		SYNTAX    DisplayString
--		ACCESS    read-write
--		STATUS    mandatory
--		DESCRIPTION
--			"Port trunk group name."
--		::= { swhPortTrunkConfigEntry 4 }
--
--	swhPortTrunkConfigPort1 OBJECT-TYPE
--		SYNTAX    INTEGER { b(0), v(1) }
--		ACCESS    read-write
--		STATUS    mandatory
--		DESCRIPTION
--			"b:Blocked  v:Member"
--		::= { swhPortTrunkConfigEntry 5 }
--
--	swhPortTrunkConfigPort2 OBJECT-TYPE
--		SYNTAX    INTEGER { b(0), v(1) }
--		ACCESS    read-write
--		STATUS    mandatory
--		DESCRIPTION
--			"b:Blocked  v:Member"
--		::= { swhPortTrunkConfigEntry 6 }
--
--	swhPortTrunkConfigPort3 OBJECT-TYPE
--		SYNTAX    INTEGER { b(0), v(1) }
--		ACCESS    read-write
--		STATUS    mandatory
--		DESCRIPTION
--			"b:Blocked  v:Member"
--		::= { swhPortTrunkConfigEntry 7 }
--
--	swhPortTrunkConfigPort4 OBJECT-TYPE
--		SYNTAX    INTEGER { b(0), v(1) }
--		ACCESS    read-write
--		STATUS    mandatory
--		DESCRIPTION
--			"b:Blocked  v:Member"
--		::= { swhPortTrunkConfigEntry 8 }
--
--	swhPortTrunkConfigPort5 OBJECT-TYPE
--		SYNTAX    INTEGER { b(0), v(1) }
--		ACCESS    read-write
--		STATUS    mandatory
--		DESCRIPTION
--			"b:Blocked  v:Member"
--		::= { swhPortTrunkConfigEntry 9 }
--
--	swhPortTrunkConfigPort6 OBJECT-TYPE
--		SYNTAX    INTEGER { b(0), v(1) }
--		ACCESS    read-write
--		STATUS    mandatory
--		DESCRIPTION
--			"b:Blocked  v:Member"
--		::= { swhPortTrunkConfigEntry 10 }
--
--
--	swhPortTrunkConfigDelete OBJECT-TYPE
--		SYNTAX    INTEGER { normal(0), delete(1) }
--		ACCESS    read-write
--		STATUS    mandatory
--		DESCRIPTION
--			"Delete this trunk setting."
--		::= { swhPortTrunkConfigEntry 56 }
--
--
-- SwitchManagement(4).LinkAggregation(45).LACPPortConfiguration(6)
--
--	swhLACPPortConfigTable OBJECT-TYPE
--		SYNTAX    SEQUENCE OF SwhLACPPortConfigEntry
--		ACCESS    not-accessible
--		STATUS    mandatory
--		DESCRIPTION
--			"Table of LACP Port descriptive and status information."
--		::= { swhLACPPortConfiguration 1 }
--
	-- Table Entry
--	swhLACPPortConfigEntry OBJECT-TYPE
--		SYNTAX    SwhLACPPortConfigEntry
--		ACCESS    not-accessible
--		STATUS    mandatory
--		DESCRIPTION
--			"An entry in the table, containing information
--			about LACP Port Config."
--		INDEX    { swhLACPPortConfigIndex }
--		::= { swhLACPPortConfigTable 1 }
--
--	SwhLACPPortConfigEntry ::=
--		SEQUENCE {
--			swhLACPPortConfigIndex
--				INTEGER,
--			swhLACPPortConfigKeyValue
--				INTEGER,
--			swhLACPPortConfigRole
--				INTEGER
--		}
--
--	swhLACPPortConfigIndex OBJECT-TYPE
--		SYNTAX    INTEGER (0..2147483647)
--		ACCESS    not-accessible
--		STATUS    mandatory
--		DESCRIPTION
--			"A unique value for each port."
--		::= { swhLACPPortConfigEntry 3 }
--
--	swhLACPPortConfigKeyValue OBJECT-TYPE
--		SYNTAX    INTEGER (0..255)
--		ACCESS    read-write
--		STATUS    mandatory
--		DESCRIPTION
--			"Path Cost is 0-255; 0=auto"
--		::= { swhLACPPortConfigEntry 9 }
--
--	swhLACPPortConfigRole OBJECT-TYPE
--		SYNTAX    INTEGER { disable(0), passive(1), active(2) }
--		ACCESS    read-write
--		STATUS    mandatory
--		DESCRIPTION
--			"Role is passive or active"
--		::= { swhLACPPortConfigEntry 12 }


-- SwitchManagement(4).IGMPSnooping(50)

	swhIGMPConfiguration
		OBJECT IDENTIFIER ::= { swhIGMPSnooping 1 }
	swhIGMPVIDConfiguration
		OBJECT IDENTIFIER ::= { swhIGMPSnooping 5 }
	swhIPMCSegment
		OBJECT IDENTIFIER ::= { swhIGMPSnooping 7 }
	swhIPMCProfile
		OBJECT IDENTIFIER ::= { swhIGMPSnooping 8 }
	swhIGMPFiltering
		OBJECT IDENTIFIER ::= { swhIGMPSnooping 9 }


-- SwitchManagement(4).IGMPSnooping(50).IGMPConfiguration(1)

	swhIGMPConfigSnooping OBJECT-TYPE
		SYNTAX    INTEGER { disable(0), enable(1) }
		ACCESS    read-write
		STATUS    mandatory
		DESCRIPTION
			"IGMP Snooping"
		::= { swhIGMPConfiguration 1 }

	swhIGMPConfigSnoopingV3 OBJECT-TYPE
		SYNTAX    INTEGER { disable(0), enable(1) }
		ACCESS    read-write
		STATUS    mandatory
		DESCRIPTION
			"IGMP Snooping v3"
		::= { swhIGMPConfiguration 60 }

	swhIGMPConfigUnregisteredIPMCFlooding OBJECT-TYPE
		SYNTAX    INTEGER { disable(0), enable(1) }
		ACCESS    read-write
		STATUS    mandatory
		DESCRIPTION
			"Unregistered IPMC Flooding"
		::= { swhIGMPConfiguration 56 }

	swhIGMPConfigQueryInterval OBJECT-TYPE
		SYNTAX    INTEGER (1..6000)
		ACCESS    read-write
		STATUS    mandatory
		DESCRIPTION
			"Query Interval (Sec)"
		::= { swhIGMPConfiguration 58 }

	swhIGMPConfigQueryResponseInterval OBJECT-TYPE
		SYNTAX    INTEGER (1..255)
		ACCESS    read-write
		STATUS    mandatory
		DESCRIPTION
			"Query Response Interval (1/10Sec)"
		::= { swhIGMPConfiguration 57 }

	swhIGMPConfigFastLeave OBJECT-TYPE
		SYNTAX    INTEGER { disable(0), enable(1) }
		ACCESS    read-write
		STATUS    mandatory
		DESCRIPTION
			"IGMP Fast Leave"
		::= { swhIGMPConfiguration 2 }

	swhIGMPConfigRouterPort1 OBJECT-TYPE
		SYNTAX    INTEGER { b(0), v(1) }
		ACCESS    read-write
		STATUS    mandatory
		DESCRIPTION
			"b:Blocked  v:Member"
		::= { swhIGMPConfiguration 5 }

	swhIGMPConfigRouterPort2 OBJECT-TYPE
		SYNTAX    INTEGER { b(0), v(1) }
		ACCESS    read-write
		STATUS    mandatory
		DESCRIPTION
			"b:Blocked  v:Member"
		::= { swhIGMPConfiguration 6 }

	swhIGMPConfigRouterPort3 OBJECT-TYPE
		SYNTAX    INTEGER { b(0), v(1) }
		ACCESS    read-write
		STATUS    mandatory
		DESCRIPTION
			"b:Blocked  v:Member"
		::= { swhIGMPConfiguration 7 }

	swhIGMPConfigRouterPort4 OBJECT-TYPE
		SYNTAX    INTEGER { b(0), v(1) }
		ACCESS    read-write
		STATUS    mandatory
		DESCRIPTION
			"b:Blocked  v:Member"
		::= { swhIGMPConfiguration 8 }

	swhIGMPConfigRouterPort5 OBJECT-TYPE
		SYNTAX    INTEGER { b(0), v(1) }
		ACCESS    read-write
		STATUS    mandatory
		DESCRIPTION
			"b:Blocked  v:Member"
		::= { swhIGMPConfiguration 9 }

	swhIGMPConfigRouterPort6 OBJECT-TYPE
		SYNTAX    INTEGER { b(0), v(1) }
		ACCESS    read-write
		STATUS    mandatory
		DESCRIPTION
			"b:Blocked  v:Member"
		::= { swhIGMPConfiguration 10 }


-- SwitchManagement(4).IGMPSnooping(50).IGMPVIDConfiguration(5).IGMPVIDConfigTable(1)

	swhIGMPVIDConfigTable OBJECT-TYPE
		SYNTAX    SEQUENCE OF SwhIGMPVIDConfigEntry
		ACCESS    not-accessible
		STATUS    mandatory
		DESCRIPTION
			"Table of IGMP VLAN ID Configuration."
		::= { swhIGMPVIDConfiguration 1 }

	-- Table Entry
	swhIGMPVIDConfigEntry OBJECT-TYPE
		SYNTAX    SwhIGMPVIDConfigEntry
		ACCESS    not-accessible
		STATUS    mandatory
		DESCRIPTION
			"An entry in the table, containing information
			about IGMP VLAN ID Config."
		INDEX    { swhIGMPVIDConfigIndex }
		::= { swhIGMPVIDConfigTable 1 }

	SwhIGMPVIDConfigEntry ::=
		SEQUENCE {
			swhIGMPVIDConfigIndex
				INTEGER,
			swhIGMPVIDConfigVLANID
				INTEGER,
--			swhIGMPVIDConfigIsMVRVID
--				INTEGER,
			swhIGMPVIDConfigVLANName
				DisplayString,
			swhIGMPVIDConfigSnooping
				INTEGER,
			swhIGMPVIDConfigQuerying
				INTEGER
		}

	swhIGMPVIDConfigIndex OBJECT-TYPE
		SYNTAX    INTEGER (0..2147483647)
		ACCESS    not-accessible
		STATUS    mandatory
		DESCRIPTION
			"A unique value for each VLAN."
		::= { swhIGMPVIDConfigEntry 1 }

	swhIGMPVIDConfigVLANName OBJECT-TYPE
		SYNTAX    DisplayString
		ACCESS    read-only
		STATUS    mandatory
		DESCRIPTION
			"VLAN Name."
		::= { swhIGMPVIDConfigEntry 5 }

	swhIGMPVIDConfigVLANID OBJECT-TYPE
		SYNTAX    INTEGER
		ACCESS    read-only
		STATUS    mandatory
		DESCRIPTION
			"VLAN ID"
		::= { swhIGMPVIDConfigEntry 7 }

	swhIGMPVIDConfigSnooping OBJECT-TYPE
		SYNTAX    INTEGER { b(0), v(1) }
		ACCESS    read-write
		STATUS    mandatory
		DESCRIPTION
			"b:Blocked  v:Member"
		::= { swhIGMPVIDConfigEntry 9 }

	swhIGMPVIDConfigQuerying OBJECT-TYPE
		SYNTAX    INTEGER { b(0), v(1) }
		ACCESS    read-write
		STATUS    mandatory
		DESCRIPTION
			"b:Blocked  v:Member"
		::= { swhIGMPVIDConfigEntry 11 }

--	swhIGMPVIDConfigIsMVRVID OBJECT-TYPE
--		SYNTAX    INTEGER { b(0), v(1) }
--		ACCESS    read-only
--		STATUS    mandatory
--		DESCRIPTION
--			"Is it MVR VLAN ID? v: yes, b: no"
--		::= { swhIGMPVIDConfigEntry 12 }


-- SwitchManagement(4).IGMPSnooping(50).IGMPSettings(6)


-- SwitchManagement(4).IGMPSnooping(50).IPMCSegment(7)

	swhIPMCSegmentTable OBJECT-TYPE
		SYNTAX    SEQUENCE OF SwhIPMCSegmentEntry
		ACCESS    not-accessible
		STATUS    mandatory
		DESCRIPTION
			"Table of IPMC Segment."
		::= { swhIPMCSegment 1 }

	-- Table Entry
	swhIPMCSegmentEntry OBJECT-TYPE
		SYNTAX    SwhIPMCSegmentEntry
		ACCESS    not-accessible
		STATUS    mandatory
		DESCRIPTION
			"An entry in the table, containing information
			about IPMC Segment."
		INDEX    { swhIPMCSegmentIndex }
		::= { swhIPMCSegmentTable 1 }

	SwhIPMCSegmentEntry ::=
		SEQUENCE {
			swhIPMCSegmentIndex
				INTEGER,
			swhIPMCSegmentValid
				INTEGER,
			swhIPMCSegmentSegmentID
				INTEGER,
			swhIPMCSegmentSegmentName
				DisplayString,
			swhIPMCSegmentIPRange1
				IpAddress,
			swhIPMCSegmentIPRange2
				IpAddress,
			swhIPMCSegmentDelete
				INTEGER
		}

	swhIPMCSegmentIndex OBJECT-TYPE
		SYNTAX    INTEGER (0..2147483647)
		ACCESS    not-accessible
		STATUS    mandatory
		DESCRIPTION
			"A unique value for each Segment."
		::= { swhIPMCSegmentEntry 1 }

	swhIPMCSegmentValid OBJECT-TYPE
		SYNTAX    INTEGER { invalid(0), valid(1) }
		ACCESS    read-only
		STATUS    mandatory
		DESCRIPTION
			"This group setting is valid or invalid."
		::= { swhIPMCSegmentEntry 2 }

	swhIPMCSegmentSegmentID OBJECT-TYPE
		SYNTAX    INTEGER (1..400)
		ACCESS    read-write
		STATUS    mandatory
		DESCRIPTION
			"Segment ID (1-400)"
		::= { swhIPMCSegmentEntry 3 }

	swhIPMCSegmentSegmentName OBJECT-TYPE
		SYNTAX    DisplayString
		ACCESS    read-write
		STATUS    mandatory
		DESCRIPTION
			"Segment Name"
		::= { swhIPMCSegmentEntry 4 }

	swhIPMCSegmentIPRange1 OBJECT-TYPE
		SYNTAX    IpAddress
		ACCESS    read-write
		STATUS    mandatory
		DESCRIPTION
			"IP Address 224.0.1.0-239.255.255.255"
		::= { swhIPMCSegmentEntry 5 }

	swhIPMCSegmentIPRange2 OBJECT-TYPE
		SYNTAX    IpAddress
		ACCESS    read-write
		STATUS    mandatory
		DESCRIPTION
			"IP Address 224.0.1.0-239.255.255.255"
		::= { swhIPMCSegmentEntry 6 }

	swhIPMCSegmentDelete OBJECT-TYPE
		SYNTAX    INTEGER { normal(0), delete(1) }
		ACCESS    read-write
		STATUS    mandatory
		DESCRIPTION
			"Delete this IPMC Segment."
		::= { swhIPMCSegmentEntry 10 }


-- SwitchManagement(4).IGMPSnooping(50).IPMCProfile(8)

	swhIPMCProfileTable OBJECT-TYPE
		SYNTAX    SEQUENCE OF SwhIPMCProfileEntry
		ACCESS    not-accessible
		STATUS    mandatory
		DESCRIPTION
			"Table of IPMC Profile."
		::= { swhIPMCProfile 1 }

	-- Table Entry
	swhIPMCProfileEntry OBJECT-TYPE
		SYNTAX    SwhIPMCProfileEntry
		ACCESS    not-accessible
		STATUS    mandatory
		DESCRIPTION
			"An entry in the table, containing information
			about IPMC Profile."
		INDEX    { swhIPMCProfileIndex }
		::= { swhIPMCProfileTable 1 }

	SwhIPMCProfileEntry ::=
		SEQUENCE {
			swhIPMCProfileIndex
				INTEGER,
			swhIPMCProfileValid
				INTEGER,
			swhIPMCProfileProfileName
				DisplayString,
			swhIPMCProfileSegment1
				INTEGER,
			swhIPMCProfileSegment2
				INTEGER,
			swhIPMCProfileSegment3
				INTEGER,
			swhIPMCProfileSegment4
				INTEGER,
			swhIPMCProfileSegment5
				INTEGER,
			swhIPMCProfileSegment6
				INTEGER,
			swhIPMCProfileSegment7
				INTEGER,
			swhIPMCProfileSegment8
				INTEGER,
			swhIPMCProfileSegment9
				INTEGER,
			swhIPMCProfileSegment10
				INTEGER,
			swhIPMCProfileDelete
				INTEGER
		}

	swhIPMCProfileIndex OBJECT-TYPE
		SYNTAX    INTEGER (0..2147483647)
		ACCESS    not-accessible
		STATUS    mandatory
		DESCRIPTION
			"A unique value for each Segment."
		::= { swhIPMCProfileEntry 1 }

	swhIPMCProfileValid OBJECT-TYPE
		SYNTAX    INTEGER { invalid(0), valid(1) }
		ACCESS    read-only
		STATUS    mandatory
		DESCRIPTION
			"This group setting is valid or invalid."
		::= { swhIPMCProfileEntry 2 }

	swhIPMCProfileProfileName OBJECT-TYPE
		SYNTAX    DisplayString
		ACCESS    read-write
		STATUS    mandatory
		DESCRIPTION
			"Segment Name"
		::= { swhIPMCProfileEntry 3 }

	swhIPMCProfileSegment1 OBJECT-TYPE
		SYNTAX    INTEGER (1..400)
		ACCESS    read-write
		STATUS    mandatory
		DESCRIPTION
			"Segment ID"
		::= { swhIPMCProfileEntry 4 }

	swhIPMCProfileSegment2 OBJECT-TYPE
		SYNTAX    INTEGER (1..400)
		ACCESS    read-write
		STATUS    mandatory
		DESCRIPTION
			"Segment ID"
		::= { swhIPMCProfileEntry 5 }

	swhIPMCProfileSegment3 OBJECT-TYPE
		SYNTAX    INTEGER (1..400)
		ACCESS    read-write
		STATUS    mandatory
		DESCRIPTION
			"Segment ID"
		::= { swhIPMCProfileEntry 6 }

	swhIPMCProfileSegment4 OBJECT-TYPE
		SYNTAX    INTEGER (1..400)
		ACCESS    read-write
		STATUS    mandatory
		DESCRIPTION
			"Segment ID"
		::= { swhIPMCProfileEntry 7 }

	swhIPMCProfileSegment5 OBJECT-TYPE
		SYNTAX    INTEGER (1..400)
		ACCESS    read-write
		STATUS    mandatory
		DESCRIPTION
			"Segment ID"
		::= { swhIPMCProfileEntry 8 }

	swhIPMCProfileSegment6 OBJECT-TYPE
		SYNTAX    INTEGER (1..400)
		ACCESS    read-write
		STATUS    mandatory
		DESCRIPTION
			"Segment ID"
		::= { swhIPMCProfileEntry 9 }

	swhIPMCProfileSegment7 OBJECT-TYPE
		SYNTAX    INTEGER (1..400)
		ACCESS    read-write
		STATUS    mandatory
		DESCRIPTION
			"Segment ID"
		::= { swhIPMCProfileEntry 10 }

	swhIPMCProfileSegment8 OBJECT-TYPE
		SYNTAX    INTEGER (1..400)
		ACCESS    read-write
		STATUS    mandatory
		DESCRIPTION
			"Segment ID"
		::= { swhIPMCProfileEntry 11 }

	swhIPMCProfileSegment9 OBJECT-TYPE
		SYNTAX    INTEGER (1..400)
		ACCESS    read-write
		STATUS    mandatory
		DESCRIPTION
			"Segment ID"
		::= { swhIPMCProfileEntry 12 }

	swhIPMCProfileSegment10 OBJECT-TYPE
		SYNTAX    INTEGER (1..400)
		ACCESS    read-write
		STATUS    mandatory
		DESCRIPTION
			"Segment ID"
		::= { swhIPMCProfileEntry 13 }

	swhIPMCProfileDelete OBJECT-TYPE
		SYNTAX    INTEGER { normal(0), delete(1) }
		ACCESS    read-write
		STATUS    mandatory
		DESCRIPTION
			"Delete this IPMC Profile."
		::= { swhIPMCProfileEntry 15 }


-- SwitchManagement(4).IGMPSnooping(50).IGMPFiltering(9)

	swhIGMPFilterState OBJECT-TYPE
		SYNTAX    INTEGER { disable(0), enable(1) }
		ACCESS    read-write
		STATUS    mandatory
		DESCRIPTION
			"Enable or disable IGMP Filter."
		::= { swhIGMPFiltering 2  }

	swhIGMPFilterTable OBJECT-TYPE
		SYNTAX    SEQUENCE OF SwhIGMPFilterEntry
		ACCESS    not-accessible
		STATUS    mandatory
		DESCRIPTION
			"Table of IGMP Filtering."
		::= { swhIGMPFiltering 1 }

	-- Table Entry
	swhIGMPFilterEntry OBJECT-TYPE
		SYNTAX    SwhIGMPFilterEntry
		ACCESS    not-accessible
		STATUS    mandatory
		DESCRIPTION
			"An entry in the table, containing information
			about IGMP Filtering."
		INDEX    { swhIGMPFilterIndex }
		::= { swhIGMPFilterTable 1 }

	SwhIGMPFilterEntry ::=
		SEQUENCE {
			swhIGMPFilterIndex
				INTEGER,
			swhIGMPFilterPortName
				DisplayString,
			swhIGMPFilterChannelLimit
				INTEGER,
			swhIGMPFilterEnable
				INTEGER,
			swhIGMPFilterIPMCProfile1
				DisplayString,
			swhIGMPFilterIPMCProfile2
				DisplayString,
			swhIGMPFilterIPMCProfile3
				DisplayString,
			swhIGMPFilterIPMCProfile4
				DisplayString
		}

	swhIGMPFilterIndex OBJECT-TYPE
		SYNTAX    INTEGER (0..2147483647)
		ACCESS    not-accessible
		STATUS    mandatory
		DESCRIPTION
			"A unique value for each port."
		::= { swhIGMPFilterEntry 1 }

	swhIGMPFilterEnable OBJECT-TYPE
		SYNTAX    INTEGER { off(0), on(1) }
		ACCESS    read-write
		STATUS    mandatory
		DESCRIPTION
			"Filter Enable"
		::= { swhIGMPFilterEntry 3 }

	swhIGMPFilterPortName OBJECT-TYPE
		SYNTAX    DisplayString
		ACCESS    read-only
		STATUS    mandatory
		DESCRIPTION
			"Port Name"
		::= { swhIGMPFilterEntry 4 }

	swhIGMPFilterIPMCProfile1 OBJECT-TYPE
		SYNTAX    DisplayString
		ACCESS    read-write
		STATUS    mandatory
		DESCRIPTION
			"IPMC Profile"
		::= { swhIGMPFilterEntry 6 }

	swhIGMPFilterIPMCProfile2 OBJECT-TYPE
		SYNTAX    DisplayString
		ACCESS    read-write
		STATUS    mandatory
		DESCRIPTION
			"IPMC Profile"
		::= { swhIGMPFilterEntry 7 }

	swhIGMPFilterIPMCProfile3 OBJECT-TYPE
		SYNTAX    DisplayString
		ACCESS    read-write
		STATUS    mandatory
		DESCRIPTION
			"IPMC Profile"
		::= { swhIGMPFilterEntry 8 }

	swhIGMPFilterIPMCProfile4 OBJECT-TYPE
		SYNTAX    DisplayString
		ACCESS    read-write
		STATUS    mandatory
		DESCRIPTION
			"IPMC Profile"
		::= { swhIGMPFilterEntry 9 }

	swhIGMPFilterChannelLimit OBJECT-TYPE
		SYNTAX    INTEGER (1..512)
		ACCESS    read-write
		STATUS    mandatory
		DESCRIPTION
			"Channel Limit (1-512), should be larger than 1 to avoid the side effect of the UPnP packets."
		::= { swhIGMPFilterEntry 10 }


-- SwitchManagement(4).8021XConfiguration(55)

	swh8021XSystemConfig
		OBJECT IDENTIFIER ::= { swh8021XConfiguration 3 }
	swh8021XPortConfig
		OBJECT IDENTIFIER ::= { swh8021XConfiguration 6 }


-- SwitchManagement(4).8021XConfiguration(55).8021XSystemConfig(3)

	swh8021XSystemConfigMode OBJECT-TYPE
		SYNTAX    INTEGER { disable(0), enable(1) }
		ACCESS    read-write
		STATUS    mandatory
		DESCRIPTION
			"Enable or disable RADIUS client."
		::= { swh8021XSystemConfig 1 }

	swh8021XSystemConfigRADIUSIP OBJECT-TYPE
		SYNTAX    DisplayString
		ACCESS    read-write
		STATUS    mandatory
		DESCRIPTION
			"RADIUS server ip address."
		::= { swh8021XSystemConfig 3 }

	swh8021XSystemConfigRADIUSSecret OBJECT-TYPE
		SYNTAX    DisplayString 
		ACCESS    read-write
		STATUS    mandatory
		DESCRIPTION
			"RADIUS Secret."
		::= { swh8021XSystemConfig 5 }

	swh8021XSystemConfigSecretKeyEncryption OBJECT-TYPE
		SYNTAX    INTEGER { disable(0), aes-128(1) }
		ACCESS    read-write
		STATUS    mandatory
		DESCRIPTION
			"Enable or disable RADIUS SecretKey Encryption."
		::= { swh8021XSystemConfig 17 }

	swh8021XSystemConfigRauthenticationEn OBJECT-TYPE
		SYNTAX    INTEGER { disable(0), enable(1) }
		ACCESS    read-write
		STATUS    mandatory
		DESCRIPTION
			"Enable or disable RADIUS client."
		::= { swh8021XSystemConfig 9 }

	swh8021XSystemConfigRadiusAssignedVLANEn OBJECT-TYPE
		SYNTAX    INTEGER { disable(0), enable(1) }
		ACCESS    read-write
		STATUS    mandatory
		DESCRIPTION
			"Enable or disable RADIUS-Assigned VLAN."
		::= { swh8021XSystemConfig 15 }

	swh8021XSystemConfigRADIUSRetryTimes OBJECT-TYPE
		SYNTAX    INTEGER (0..5)
		ACCESS    read-write
		STATUS    mandatory
		DESCRIPTION
			"RADIUS Retry Times"
		::= { swh8021XSystemConfig 18 }

	swh8021XSystemConfigRADIUSTimeout OBJECT-TYPE
		SYNTAX    INTEGER (1..30)
		ACCESS    read-write
		STATUS    mandatory
		DESCRIPTION
			"RADIUS Timeout"
		::= { swh8021XSystemConfig 19 }


-- SwitchManagement(4).8021XConfiguration(55).8021XPortConfig(6).8021XPortConfigTable(1)

	swh8021XPortConfigTable OBJECT-TYPE
		SYNTAX    SEQUENCE OF Swh8021XPortConfigEntry
		ACCESS    not-accessible
		STATUS    mandatory
		DESCRIPTION
			"Table of 802.1X Port Configuration."
		::= { swh8021XPortConfig 1 }

	-- Table Entry
	swh8021XPortConfigEntry OBJECT-TYPE
		SYNTAX    Swh8021XPortConfigEntry
		ACCESS    not-accessible
		STATUS    mandatory
		DESCRIPTION
			"An entry in the table, containing information
			about 802.1X Port Config."
		INDEX    { swh8021XPortConfigIndex }
		::= { swh8021XPortConfigTable 1 }

	Swh8021XPortConfigEntry ::=
		SEQUENCE {
			swh8021XPortConfigIndex
				INTEGER,
			swh8021XPortConfigAdminState
				INTEGER,
			swh8021XPortConfigMAB
				INTEGER,
			swh8021XPortConfigRadiusAssignedVLAN
				INTEGER,
			swh8021XPortConfigFailAction
				INTEGER,
			swh8021XPortConfigFailVLAN
				INTEGER,
			swh8021XPortConfigNoResponseAction
				INTEGER,
			swh8021XPortConfigNoResponseVLAN
				INTEGER,
			swh8021XPortConfigNoServerAction
				INTEGER,
			swh8021XPortConfigNoServerVLAN
				INTEGER,
			swh8021XPortConfigreAuthEnable
				INTEGER,
			swh8021XPortConfigreAuthSec
				INTEGER,
			swh8021XPortConfigEAPTimeout
				INTEGER,
			swh8021XPortConfigMaxreq
				INTEGER,
			swh8021XPortConfigReauthenticate
				INTEGER
		}

	swh8021XPortConfigIndex OBJECT-TYPE
		SYNTAX    INTEGER (0..2147483647)
		ACCESS    not-accessible
		STATUS    mandatory
		DESCRIPTION
			"A unique value for each Port."
		::= { swh8021XPortConfigEntry 1 }

	swh8021XPortConfigAdminState OBJECT-TYPE
		SYNTAX    INTEGER { auto(0), authorized(1), unauthorized(2) }
		ACCESS    read-write
		STATUS    mandatory
		DESCRIPTION
			"Admin State setting is auto or authorized or unauthorized."
		::= { swh8021XPortConfigEntry 3 }

	swh8021XPortConfigReauthenticate OBJECT-TYPE
		SYNTAX    INTEGER { disable(0), enable(1) }
		ACCESS    read-write
		STATUS    mandatory
		DESCRIPTION
			"Reauthenticate is Disable or Enable"
		::= { swh8021XPortConfigEntry 5 }

	swh8021XPortConfigRadiusAssignedVLAN OBJECT-TYPE
		SYNTAX    INTEGER { disable(0), enable(1) }
		ACCESS    read-write
		STATUS    mandatory
		DESCRIPTION
			"Radius-Assigned VLAN is Disable or Enable"
		::= { swh8021XPortConfigEntry 7 }

	swh8021XPortConfigMAB OBJECT-TYPE
		SYNTAX    INTEGER { disable(0), enable(1) }
		ACCESS    read-write
		STATUS    mandatory
		DESCRIPTION
			"MAB is Disable or Enable"
		::= { swh8021XPortConfigEntry 9 }

	swh8021XPortConfigreAuthEnable OBJECT-TYPE
		SYNTAX    INTEGER { disable(0), enable(1) }
		ACCESS    read-write
		STATUS    mandatory
		DESCRIPTION
			"reAuth Enable is Disable or Enable"
		::= { swh8021XPortConfigEntry 11 }

	swh8021XPortConfigreAuthSec OBJECT-TYPE
		SYNTAX    INTEGER (1..65535)
		ACCESS    read-write
		STATUS    mandatory
		DESCRIPTION
			"reAuth Sec Per Port"
		::= { swh8021XPortConfigEntry 13 }

	swh8021XPortConfigEAPTimeout OBJECT-TYPE
		SYNTAX    INTEGER (1..255)
		ACCESS    read-write
		STATUS    mandatory
		DESCRIPTION
			"EAP Timeout Per Port"
		::= { swh8021XPortConfigEntry 15 }

	swh8021XPortConfigMaxreq OBJECT-TYPE
		SYNTAX    INTEGER (1..10)
		ACCESS    read-write
		STATUS    mandatory
		DESCRIPTION
			"Maxreq Per Port"
		::= { swh8021XPortConfigEntry 17 }

	swh8021XPortConfigFailAction OBJECT-TYPE
		SYNTAX    INTEGER { block(0), authorizevlan(1) }
		ACCESS    read-write
		STATUS    mandatory
		DESCRIPTION
			"Fail Action is block or authorize vlan"
		::= { swh8021XPortConfigEntry 18 }

	swh8021XPortConfigFailVLAN OBJECT-TYPE
		SYNTAX    INTEGER (1..4094)
		ACCESS    read-write
		STATUS    mandatory
		DESCRIPTION
			"Fail VLAN Per Port"
		::= { swh8021XPortConfigEntry 19 }

	swh8021XPortConfigNoResponseAction OBJECT-TYPE
		SYNTAX    INTEGER { block(0), authorizevlan(1) }
		ACCESS    read-write
		STATUS    mandatory
		DESCRIPTION
			"NoResponse Action is block or authorize vlan"
		::= { swh8021XPortConfigEntry 20 }

	swh8021XPortConfigNoResponseVLAN OBJECT-TYPE
		SYNTAX    INTEGER (1..4094)
		ACCESS    read-write
		STATUS    mandatory
		DESCRIPTION
			"NoResponse VLAN Per Port"
		::= { swh8021XPortConfigEntry 21 }

	swh8021XPortConfigNoServerAction OBJECT-TYPE
		SYNTAX    INTEGER { block(0), authorizevlan(1) }
		ACCESS    read-write
		STATUS    mandatory
		DESCRIPTION
			"NoServer Action is block or authorize vlan"
		::= { swh8021XPortConfigEntry 22 }

	swh8021XPortConfigNoServerVLAN OBJECT-TYPE
		SYNTAX    INTEGER (1..4094)
		ACCESS    read-write
		STATUS    mandatory
		DESCRIPTION
			"NoServer VLAN Per Port"
		::= { swh8021XPortConfigEntry 23 }


-- SwitchManagement(4).QoSConfiguration(60)

	swhQoSConfigPriority
		OBJECT IDENTIFIER ::= { swhQoSConfiguration 1 }
	swhQoSConfigPortConfig
		OBJECT IDENTIFIER ::= { swhQoSConfiguration 3 }
	swhQoSConfigRateLimiters
		OBJECT IDENTIFIER ::= { swhQoSConfiguration 9 }


-- SwitchManagement(4).QoSConfiguration(60).QoSConfigPriority(1)

	swhQoSConfigPriorityMode OBJECT-TYPE
		SYNTAX    INTEGER { disabled(0), ieee8021p(2), dscp(3) }
		ACCESS    read-write
		STATUS    mandatory
		DESCRIPTION
			"Specify QoS mode"
		::= { swhQoSConfigPriority 1 }

	swhQoSConfigPriorityQueuingMode OBJECT-TYPE
		SYNTAX    INTEGER { weight(0), strict(1) }
		ACCESS    read-write
		STATUS    mandatory
		DESCRIPTION
			"Specify the queue mode is Strict or Weight"
		::= { swhQoSConfigPriority 2 }

	swhQoSConfigPriorityQueueWeighted OBJECT-TYPE
		SYNTAX    DisplayString (SIZE (0..255))
		ACCESS    read-write
		STATUS    mandatory
		DESCRIPTION
			"Specify as weight (Q0:Q1:Q2:Q3:Q4:Q5:Q6:Q7) , Queue is 1~1023"
		::= { swhQoSConfigPriority 11 }

	swhQoSConfigPriorityManagementPriority OBJECT-TYPE
		SYNTAX    INTEGER (0..7)
		ACCESS    read-write
		STATUS    mandatory
		DESCRIPTION
			"Specify Management Priority(0-7)."
		::= { swhQoSConfigPriority 10 }

	swhQoSConfigPriority8021pRemarking OBJECT-TYPE
		SYNTAX    INTEGER { disable(0), enable(1) }
		ACCESS    read-write
		STATUS    mandatory
		DESCRIPTION
			"Specify 802.1p Remarking"
		::= { swhQoSConfigPriority 30 }

	swhQoSConfigPriorityDSCPRemarking OBJECT-TYPE
	--	SYNTAX    INTEGER { disable(0), by-dscp(1), by-port(2) }
		SYNTAX    INTEGER { disable(0), enable(1) }
		ACCESS    read-write
		STATUS    mandatory
		DESCRIPTION
			"Specify DSCP Remarking"
		::= { swhQoSConfigPriority 40 }


-- SwitchManagement(4).QoSConfiguration(60).QoSConfigPriority(1).QoSConfig8021pPriorityTable(5)

	swhQoSConfig8021pPriorityTable OBJECT-TYPE
		SYNTAX    SEQUENCE OF SwhQoSConfig8021pPriorityEntry
		ACCESS    not-accessible
		STATUS    mandatory
		DESCRIPTION
			"Table of 802.1p Priority Map."
		::= { swhQoSConfigPriority 5 }

	-- Table Entry
	swhQoSConfig8021pPriorityEntry OBJECT-TYPE
		SYNTAX    SwhQoSConfig8021pPriorityEntry
		ACCESS    not-accessible
		STATUS    mandatory
		DESCRIPTION
			"An entry in the table, containing information
			about 802.1p Priority config."
		INDEX    { swhQoSConfig8021pPriorityIndex }
		::= { swhQoSConfig8021pPriorityTable 1 }

	SwhQoSConfig8021pPriorityEntry ::=
		SEQUENCE {
			swhQoSConfig8021pPriorityIndex
				INTEGER,
			swhQoSConfig8021pPriorityPriority
				INTEGER,
			swhQoSConfig8021pPriorityQueue
				INTEGER
		}

	swhQoSConfig8021pPriorityIndex OBJECT-TYPE
		SYNTAX    INTEGER (0..2147483647)
		ACCESS    not-accessible
		STATUS    mandatory
		DESCRIPTION
			"A unique value for each 802.1p priority."
		::= { swhQoSConfig8021pPriorityEntry 1 }

	swhQoSConfig8021pPriorityPriority OBJECT-TYPE
		SYNTAX    INTEGER { dot1p-0(0),
		                    dot1p-1(1),
		                    dot1p-2(2),
		                    dot1p-3(3),
		                    dot1p-4(4),
		                    dot1p-5(5),
		                    dot1p-6(6),
		                    dot1p-7(7)
		                    } 
		ACCESS    read-only
		STATUS    mandatory
		DESCRIPTION
			"802.1p priority."
		::= { swhQoSConfig8021pPriorityEntry 2 }

	swhQoSConfig8021pPriorityQueue OBJECT-TYPE
		SYNTAX    INTEGER { q0(0), q1(1), q2(2), q3(3), q4(4), q5(5), q6(6), q7(7) }
		ACCESS    read-write
		STATUS    mandatory
		DESCRIPTION
			"Specify 802.1p bit value, Q0 Q1 Q2 Q3 Q4 Q5 Q6 Q7."
		::= { swhQoSConfig8021pPriorityEntry 3 }


-- SwitchManagement(4).QoSConfiguration(60).QoSConfigPriority(1).QoSConfigDSCPPriorityTable(6)

	swhQoSConfigDSCPPriorityTable OBJECT-TYPE
		SYNTAX    SEQUENCE OF SwhQoSConfigDSCPPriorityEntry
		ACCESS    not-accessible
		STATUS    mandatory
		DESCRIPTION
			"Table of DSCP Priority Map."
		::= { swhQoSConfigPriority 6 }

	-- Table Entry
	swhQoSConfigDSCPPriorityEntry OBJECT-TYPE
		SYNTAX    SwhQoSConfigDSCPPriorityEntry
		ACCESS    not-accessible
		STATUS    mandatory
		DESCRIPTION
			"An entry in the table, containing information
			about DSCP Priority config."
		INDEX    { swhQoSConfigDSCPPriorityIndex }
		::= { swhQoSConfigDSCPPriorityTable 1 }

	SwhQoSConfigDSCPPriorityEntry ::=
		SEQUENCE {
			swhQoSConfigDSCPPriorityIndex
				INTEGER,
			swhQoSConfigDSCPPriorityPriority
				INTEGER,
			swhQoSConfigDSCPPriorityQueue
				INTEGER
		}

	swhQoSConfigDSCPPriorityIndex OBJECT-TYPE
		SYNTAX    INTEGER (0..2147483647)
		ACCESS    not-accessible
		STATUS    mandatory
		DESCRIPTION
			"A unique value for each dscp priority."
		::= { swhQoSConfigDSCPPriorityEntry 1 }

	swhQoSConfigDSCPPriorityPriority OBJECT-TYPE
		SYNTAX    INTEGER { dscp-0(0), dscp-1(1), dscp-2(2), dscp-3(3),
		                    dscp-4(4), dscp-5(5), dscp-6(6), dscp-7(7),
		                    dscp-8(8), dscp-9(9), dscp-10(10), dscp-11(11),
		                    dscp-12(12), dscp-13(13), dscp-14(14), dscp-15(15),
		                    dscp-16(16), dscp-17(17), dscp-18(18), dscp-19(19),
		                    dscp-20(20), dscp-21(21), dscp-22(22), dscp-23(23),
		                    dscp-24(24), dscp-25(25), dscp-26(26), dscp-27(27),
		                    dscp-28(28), dscp-29(29), dscp-30(30), dscp-31(31),
		                    dscp-32(32), dscp-33(33), dscp-34(34), dscp-35(35),
		                    dscp-36(36), dscp-37(37), dscp-38(38), dscp-39(39),
		                    dscp-40(40), dscp-41(41), dscp-42(42), dscp-43(43),
		                    dscp-44(44), dscp-45(45), dscp-46(46), dscp-47(47),
		                    dscp-48(48), dscp-49(49), dscp-50(50), dscp-51(51),
		                    dscp-52(52), dscp-53(53), dscp-54(54), dscp-55(55),
		                    dscp-56(56), dscp-57(57), dscp-58(58), dscp-59(59),
		                    dscp-60(60), dscp-61(61), dscp-62(62), dscp-63(63)
		                    }
		ACCESS    read-only
		STATUS    mandatory
		DESCRIPTION
			"DSCP priority."
		::= { swhQoSConfigDSCPPriorityEntry 2 }

	swhQoSConfigDSCPPriorityQueue OBJECT-TYPE
		SYNTAX    INTEGER { q0(0), q1(1), q2(2), q3(3), q4(4), q5(5), q6(6), q7(7) }
		ACCESS    read-write
		STATUS    mandatory
		DESCRIPTION
			"Specify DSCP bit value, Q0 Q1 Q2 Q3 Q4 Q5 Q6 Q7."
		::= { swhQoSConfigDSCPPriorityEntry 3 }


-- SwitchManagement(4).QoSConfiguration(60).QoSConfigPriority(1).QoSConfig8021pRemarkingTable(31)

	swhQoSConfig8021pRemarkingTable OBJECT-TYPE
		SYNTAX    SEQUENCE OF SwhQoSConfig8021pRemarkingEntry
		ACCESS    not-accessible
		STATUS    mandatory
		DESCRIPTION
			"Table of 802.1p Remarking Map."
		::= { swhQoSConfigPriority 31 }

	-- Table Entry
	swhQoSConfig8021pRemarkingEntry OBJECT-TYPE
		SYNTAX    SwhQoSConfig8021pRemarkingEntry
		ACCESS    not-accessible
		STATUS    mandatory
		DESCRIPTION
			"An entry in the table, containing information
			about 802.1p Remarking config."
		INDEX    { swhQoSConfig8021pRemarkingIndex }
		::= { swhQoSConfig8021pRemarkingTable 1 }

	SwhQoSConfig8021pRemarkingEntry ::=
		SEQUENCE {
			swhQoSConfig8021pRemarkingIndex
				INTEGER,
			swhQoSConfig8021pRemarkingRx8021p
				INTEGER,
			swhQoSConfig8021pRemarkingNew8021p
				INTEGER
		}

	swhQoSConfig8021pRemarkingIndex OBJECT-TYPE
		SYNTAX    INTEGER (0..2147483647)
		ACCESS    not-accessible
		STATUS    mandatory
		DESCRIPTION
			"A unique value for each 802.1p remarking index."
		::= { swhQoSConfig8021pRemarkingEntry 1 }

	--swhQoSConfig8021pRemarkingQueue OBJECT-TYPE
	--	SYNTAX    INTEGER { q0(0), q1(1), q2(2), q3(3) }
	--	ACCESS    read-only
	--	STATUS    mandatory
	--	DESCRIPTION
	--		"Specify 802.1p bit value, Q0 Q1 Q2 Q3."
	--	::= { swhQoSConfig8021pRemarkingEntry 2 }

	swhQoSConfig8021pRemarkingNew8021p OBJECT-TYPE
		SYNTAX    INTEGER (0..7)
		ACCESS    read-write
		STATUS    mandatory
		DESCRIPTION
			"New-802.1p(0-7)."
		::= { swhQoSConfig8021pRemarkingEntry 3 }

	--swhQoSConfig8021pRemarkingState OBJECT-TYPE
	--	SYNTAX    INTEGER { disable(0), enable(1) }
	--	ACCESS    read-write
	--	STATUS    mandatory
	--	DESCRIPTION
	--		"disable or enable 802.1p remarking priority"
	--	::= { swhQoSConfig8021pRemarkingEntry 4 }

	swhQoSConfig8021pRemarkingRx8021p OBJECT-TYPE
		SYNTAX    INTEGER (0..7)
		ACCESS    read-only
		STATUS    mandatory
		DESCRIPTION
			"Rx-802.1p(0-7)."
		::= { swhQoSConfig8021pRemarkingEntry 5 }

	--swhQoSConfig8021pRemarkingRxDSCP OBJECT-TYPE
	--	SYNTAX    INTEGER (0..63)
	--	ACCESS    read-write
	--	STATUS    mandatory
	--	DESCRIPTION
	--		"Rx-DSCP(0-63)."
	--	::= { swhQoSConfig8021pRemarkingEntry 6 }


-- SwitchManagement(4).QoSConfiguration(60).QoSConfigPriority(1).QoSConfigDSCPRemarkingTable(41)

	swhQoSConfigDSCPRemarkingTable OBJECT-TYPE
		SYNTAX    SEQUENCE OF SwhQoSConfigDSCPRemarkingEntry
		ACCESS    not-accessible
		STATUS    mandatory
		DESCRIPTION
			"Table of DSCP Remarking Map."
		::= { swhQoSConfigPriority 41 }

	-- Table Entry
	swhQoSConfigDSCPRemarkingEntry OBJECT-TYPE
		SYNTAX    SwhQoSConfigDSCPRemarkingEntry
		ACCESS    not-accessible
		STATUS    mandatory
		DESCRIPTION
			"An entry in the table, containing information
			about DSCP Remarking config."
		INDEX    { swhQoSConfigDSCPRemarkingIndex }
		::= { swhQoSConfigDSCPRemarkingTable 1 }

	SwhQoSConfigDSCPRemarkingEntry ::=
		SEQUENCE {
			swhQoSConfigDSCPRemarkingIndex
				INTEGER,
			swhQoSConfigDSCPRemarkingRxDSCP
				INTEGER,
			swhQoSConfigDSCPRemarkingNewDSCP
				INTEGER
		}

	swhQoSConfigDSCPRemarkingIndex OBJECT-TYPE
		SYNTAX    INTEGER (0..2147483647)
		ACCESS    not-accessible
		STATUS    mandatory
		DESCRIPTION
			"A unique value for each dscp remarking index."
		::= { swhQoSConfigDSCPRemarkingEntry 1 }

	--swhQoSConfigDSCPRemarkingQueue OBJECT-TYPE
	--	SYNTAX    INTEGER { q0(0), q1(1), q2(2), q3(3) }
	--	ACCESS    read-only
	--	STATUS    mandatory
	--	DESCRIPTION
	--		"Specify DSCP bit value, Q0 Q1 Q2 Q3."
	--	::= { swhQoSConfigDSCPRemarkingEntry 2 }

	swhQoSConfigDSCPRemarkingNewDSCP OBJECT-TYPE
		SYNTAX    INTEGER (0..63)
		ACCESS    read-write
		STATUS    mandatory
		DESCRIPTION
			"DSCP priority(0-63)."
		::= { swhQoSConfigDSCPRemarkingEntry 3 }

	--swhQoSConfigDSCPRemarkingState OBJECT-TYPE
	--	SYNTAX    INTEGER { disable(0), enable(1) }
	--	ACCESS    read-write
	--	STATUS    mandatory
	--	DESCRIPTION
	--		"disable or enable DSCP remarking"
	--	::= { swhQoSConfigDSCPRemarkingEntry 4 }

	swhQoSConfigDSCPRemarkingRxDSCP OBJECT-TYPE
		SYNTAX    INTEGER (0..63)
		ACCESS    read-write
		STATUS    mandatory
		DESCRIPTION
			"DSCP(0-63)."
		::= { swhQoSConfigDSCPRemarkingEntry 5 }


-- SwitchManagement(4).QoSConfiguration(60).QoSConfigPortConfig(3).QoSConfigPortConfigTable(1)

	swhQoSConfigPortConfigTable OBJECT-TYPE
		SYNTAX    SEQUENCE OF SwhQoSConfigPortConfigEntry
		ACCESS    not-accessible
		STATUS    mandatory
		DESCRIPTION
			"Table of QoS Port Configuration."
		::= { swhQoSConfigPortConfig 1 }

	-- Table Entry
	swhQoSConfigPortConfigEntry OBJECT-TYPE
		SYNTAX    SwhQoSConfigPortConfigEntry
		ACCESS    not-accessible
		STATUS    mandatory
		DESCRIPTION
			"An entry in the table, containing information
			about QoS Port Configuration."
		INDEX    { swhQoSConfigPortConfigIndex }
		::= { swhQoSConfigPortConfigTable 1 }

	SwhQoSConfigPortConfigEntry ::=
		SEQUENCE {
			swhQoSConfigPortConfigIndex
				INTEGER,
		--	swhQoSConfigPortConfigDefaultClass
		--		INTEGER,
			swhQoSConfigPortConfigUserPriority
				INTEGER
		}

	swhQoSConfigPortConfigIndex OBJECT-TYPE
		SYNTAX    INTEGER (0..2147483647)
		ACCESS    not-accessible
		STATUS    mandatory
		DESCRIPTION
			"A unique value for each Port."
		::= { swhQoSConfigPortConfigEntry 1 }

	--swhQoSConfigPortConfigDefaultClass OBJECT-TYPE
	--	SYNTAX    INTEGER { low(0), normal(1), medium(2), high(3) }
	--	ACCESS    read-write
	--	STATUS    mandatory
	--	DESCRIPTION
	--		"This VLAN setting is valid or invalid."
	--	::= { swhQoSConfigPortConfigEntry 3 }

	--swhQoSConfigPortConfigQCL OBJECT-TYPE
	--	SYNTAX    INTEGER { 1.(0),
	--	                    2.(1),
	--	                    3.(2),
	--	                    4.(3),
	--	                    5.(4),
	--	                    6.(5),
	--	                    7.(6),
	--	                    8.(7),
	--	                    9.(8),
	--	                    10.(9),
	--	                    11.(10),
	--	                    12.(11),
	--	                    13.(12),
	--	                    14.(13),
	--	                    15.(14),
	--	                    16.(15),
	--	                    17.(16),
	--	                    18.(17),
	--	                    19.(18),
	--	                    20.(19),
	--	                    21.(20),
	--	                    22.(21),
	--	                    23.(22),
	--	                    24.(23),
	--	                    25.(24),
	--	                    26.(25)
	--	                    }
	--	ACCESS    read-write
	--	STATUS    mandatory
	--	DESCRIPTION
	--		"QCL Number 1-26"
	--	::= { swhQoSConfigPortConfigEntry 5 }

	swhQoSConfigPortConfigUserPriority OBJECT-TYPE
		SYNTAX    INTEGER
		ACCESS    read-write
		STATUS    mandatory
		DESCRIPTION
			"User Priority 0-7"
		::= { swhQoSConfigPortConfigEntry 7 }

	--swhQoSConfigPortConfigQueuingMode OBJECT-TYPE
	--	SYNTAX    INTEGER { strict(0), weight(1) }
	--	ACCESS    read-write
	--	STATUS    mandatory
	--	DESCRIPTION
	--		"Queuing Mode setting is strict or weight."
	--	::= { swhQoSConfigPortConfigEntry 9 }

	--swhQoSConfigPortConfigQueueWeightedLow OBJECT-TYPE
	--	SYNTAX    INTEGER { 1.(0), 2.(1), 4.(2), 8.(3) }
	--	ACCESS    read-write
	--	STATUS    mandatory
	--	DESCRIPTION
	--		"Queue Weighted Low setting is 1/2/4/8."
	--	::= { swhQoSConfigPortConfigEntry 11 }

	--swhQoSConfigPortConfigQueueWeightedNormal OBJECT-TYPE
	--	SYNTAX    INTEGER { 1.(0), 2.(1), 4.(2), 8.(3) }
	--	ACCESS    read-write
	--	STATUS    mandatory
	--	DESCRIPTION
	--		"Queue Weighted Normal setting is 1/2/4/8."
	--	::= { swhQoSConfigPortConfigEntry 13 }

	--swhQoSConfigPortConfigQueueWeightedMedium OBJECT-TYPE
	--	SYNTAX    INTEGER { 1.(0), 2.(1), 4.(2), 8.(3) }
	--	ACCESS    read-write
	--	STATUS    mandatory
	--	DESCRIPTION
	--		"Queue Weighted Medium setting is 1/2/4/8."
	--	::= { swhQoSConfigPortConfigEntry 15 }

	--swhQoSConfigPortConfigQueueWeightedHigh OBJECT-TYPE
	--	SYNTAX    INTEGER { 1.(0), 2.(1), 4.(2), 8.(3) }
	--	ACCESS    read-write
	--	STATUS    mandatory
	--	DESCRIPTION
	--		"Queue Weighted High setting is 1/2/4/8."
	--	::= { swhQoSConfigPortConfigEntry 17 }


-- SwitchManagement(4).QoSConfiguration(60).QoSConfigControlList(6)


-- SwitchManagement(4).QoSConfiguration(60).QoSConfigRateLimiters(9)


-- SwitchManagement(4).QoSConfiguration(60).QoSConfigRateLimiters(9).QoSConfigRateLimitersTable(1)

	swhQoSConfigRateLimitersTable OBJECT-TYPE
		SYNTAX    SEQUENCE OF SwhQoSConfigRateLimitersEntry
		ACCESS    not-accessible
		STATUS    mandatory
		DESCRIPTION
			"Table of QoS Rate Limiters."
		::= { swhQoSConfigRateLimiters 1 }

	-- Table Entry
	swhQoSConfigRateLimitersEntry OBJECT-TYPE
		SYNTAX    SwhQoSConfigRateLimitersEntry
		ACCESS    not-accessible
		STATUS    mandatory
		DESCRIPTION
			"An entry in the table, containing information
			about QoS Rate Limiters."
		INDEX    { swhQoSConfigRateLimitersIndex }
		::= { swhQoSConfigRateLimitersTable 1 }

	SwhQoSConfigRateLimitersEntry ::=
		SEQUENCE {
			swhQoSConfigRateLimitersIndex
				INTEGER,
			swhQoSConfigRateLimitersIngressEnable
				INTEGER,
			swhQoSConfigRateLimitersIngressRate
				INTEGER,
			swhQoSConfigRateLimitersIngressUnit
				INTEGER,
			swhQoSConfigRateLimitersEgressEnable
				INTEGER,
			swhQoSConfigRateLimitersEgressRate
				INTEGER,
			swhQoSConfigRateLimitersEgressUnit
				INTEGER
		}

	swhQoSConfigRateLimitersIndex OBJECT-TYPE
		SYNTAX    INTEGER (0..2147483647)
		ACCESS    not-accessible
		STATUS    mandatory
		DESCRIPTION
			"A unique value for each Port."
		::= { swhQoSConfigRateLimitersEntry 1 }

	swhQoSConfigRateLimitersIngressRate OBJECT-TYPE
		SYNTAX    INTEGER (500..10000000)
		ACCESS    read-write
		STATUS    mandatory
		DESCRIPTION
			"This VLAN setting is valid or invalid."
		::= { swhQoSConfigRateLimitersEntry 3 }

	swhQoSConfigRateLimitersEgressRate OBJECT-TYPE
		SYNTAX    INTEGER (500..10000000)
		ACCESS    read-write
		STATUS    mandatory
		DESCRIPTION
			"Reauthenticate is Disable or Enable"
		::= { swhQoSConfigRateLimitersEntry 5 }

	swhQoSConfigRateLimitersIngressEnable OBJECT-TYPE
		SYNTAX    INTEGER { disable(0), enable(1) }
		ACCESS    read-write
		STATUS    mandatory
		DESCRIPTION
			"Rate Limiters Ingress is Disable or Enable"
		::= { swhQoSConfigRateLimitersEntry 6 }

	swhQoSConfigRateLimitersIngressUnit OBJECT-TYPE
		SYNTAX    INTEGER { kbps(0), mbps(1) }
		ACCESS    read-write
		STATUS    mandatory
		DESCRIPTION
			"Rate Limiters Ingress Unit is Kbps or Mbps"
		::= { swhQoSConfigRateLimitersEntry 7 }

	swhQoSConfigRateLimitersEgressEnable OBJECT-TYPE
		SYNTAX    INTEGER { disable(0), enable(1) }
		ACCESS    read-write
		STATUS    mandatory
		DESCRIPTION
			"Rate Limiters Egress is Disable or Enable"
		::= { swhQoSConfigRateLimitersEntry 8 }

	swhQoSConfigRateLimitersEgressUnit OBJECT-TYPE
		SYNTAX    INTEGER { kbps(0), mbps(1) }
		ACCESS    read-write
		STATUS    mandatory
		DESCRIPTION
			"Rate Limiters Egress Unit is Kbps or Mbps"
		::= { swhQoSConfigRateLimitersEntry 9 }


-- SwitchManagement(4).QoSConfiguration(60).QoSConfigStormControl(12)


-- SwitchManagement(4).DSCPRemark(61)


-- SwitchManagement(4).DSCPRemark(61).PortDSCPRemarking(1)


-- SwitchManagement(4).DSCPRemark(61).Port8021pRemarking(2)


-- SwitchManagement(4).DSCPRemark(61).DSCPQueueMapping(3)


-- SwitchManagement(4).DSCPRemark(61).8021pQueueMapping(4)


-- SwitchManagement(4).DSCPRemarkingvoip(63)


-- SwitchManagement(4).ACLConfiguration(65)

	swhAccessControlListIPv4
		OBJECT IDENTIFIER ::= { swhACLConfiguration 4 }

	swhAccessControlListIPv6
		OBJECT IDENTIFIER ::= { swhACLConfiguration 5 }


-- SwitchManagement(4).ACLConfiguration(65).ACLPortConfiguration(1)


-- SwitchManagement(4).ACLConfiguration(65).ACLRateLimiters(2)


-- SwitchManagement(4).ACLConfiguration(65).AccessControlList(3)


-- SwitchManagement(4).ACLConfiguration(65).AccessControlListIPv4(4)

	swhAccessControlListIPv4Table OBJECT-TYPE
		SYNTAX    SEQUENCE OF SwhAccessControlListIPv4Entry
		ACCESS    not-accessible
		STATUS    mandatory
		DESCRIPTION
			"Table of Access Control List."
		::= { swhAccessControlListIPv4 1 }

	-- Table Entry
	swhAccessControlListIPv4Entry OBJECT-TYPE
		SYNTAX    SwhAccessControlListIPv4Entry
		ACCESS    not-accessible
		STATUS    mandatory
		DESCRIPTION
			"An entry in the table, containing information
			 about Access Control List."
		INDEX    { swhAccessControlListIPv4Index }
		::= { swhAccessControlListIPv4Table 1 }

	SwhAccessControlListIPv4Entry ::=
		SEQUENCE {
			swhAccessControlListIPv4Index
				INTEGER,
			swhAccessControlListIPv4Valid
				INTEGER,
			swhAccessControlListIPv4RuleID
				INTEGER,
			swhAccessControlListIPv4Name
				DisplayString,
			swhAccessControlListIPv4Sequence
				INTEGER,
			swhAccessControlListIPv4Enable
				INTEGER,
			swhAccessControlListIPv4IngressPortFilter
			    INTEGER,
			swhAccessControlListIPv4IngressPort
				DisplayString,
			swhAccessControlListIPv4EtherTypeFilter
				INTEGER,
			swhAccessControlListIPv4EthernetTypeValue
				DisplayString,
			swhAccessControlListIPv4VLANIDFilter
				INTEGER,
			swhAccessControlListIPv4VLANID
				INTEGER,
			swhAccessControlListIPv4SourceMACFilter
				INTEGER,
			swhAccessControlListIPv4SourceMACValue
				DisplayString,
			swhAccessControlListIPv4SourceMACMask
				DisplayString,
			swhAccessControlListIPv4DestinationMACFilter
				INTEGER,
			swhAccessControlListIPv4DestinationMACValue
				DisplayString,
			swhAccessControlListIPv4DestinationMACMask
				DisplayString,
			swhAccessControlListIPv4TOSTrafficClassFilter
				INTEGER,
			swhAccessControlListIPv4TOSTrafficClass
				DisplayString,
			swhAccessControlListIPv4ProtocolNextHeaderFilter
				INTEGER,
			swhAccessControlListIPv4ProtocolNextHeader
				DisplayString,
			swhAccessControlListIPv4IPv4SourceIPFilter
				INTEGER,
			swhAccessControlListIPv4IPv4SourceIPAddress
				DisplayString,
			swhAccessControlListIPv4IPv4SourceIPMask
				DisplayString,
			swhAccessControlListIPv4IPv4DestinationIPFilter
				INTEGER,
			swhAccessControlListIPv4IPv4DestinationIPAddress
				DisplayString,
			swhAccessControlListIPv4IPv4DestinationIPMask
				DisplayString,
			swhAccessControlListIPv4TCPUDPSourcePortFilter
				INTEGER,
			swhAccessControlListIPv4TCPUDPSourcePort
				INTEGER,
			swhAccessControlListIPv4TCPUDPSourcePortMask
				DisplayString,
			swhAccessControlListIPv4TCPUDPDestinationPortFilter
				INTEGER,
			swhAccessControlListIPv4TCPUDPDestinationPort
				INTEGER,
			swhAccessControlListIPv4TCPUDPDestinationPortMask
				DisplayString,
			swhAccessControlListIPv4Action
				INTEGER,
			swhAccessControlListIPv4PortCopy
				INTEGER,
			swhAccessControlListIPv4RateLimiter
				INTEGER,
			swhAccessControlListIPv4Apply
				INTEGER,
			swhAccessControlListIPv4Delete
				INTEGER
		}

	swhAccessControlListIPv4Index OBJECT-TYPE
		SYNTAX    INTEGER (0..2147483647)
		ACCESS    not-accessible
		STATUS    mandatory
		DESCRIPTION
			"A unique value for Access Control List."
		::= { swhAccessControlListIPv4Entry 1 }

	swhAccessControlListIPv4Valid OBJECT-TYPE
		SYNTAX    INTEGER { valid(1), invalid(0) }
		ACCESS    read-only
		STATUS    mandatory
		DESCRIPTION
			"Valid"
		::= { swhAccessControlListIPv4Entry 2 }

	swhAccessControlListIPv4RuleID OBJECT-TYPE
		SYNTAX    INTEGER (1..110)
		ACCESS    read-only
		STATUS    mandatory
		DESCRIPTION
			"Rule ID (1-192)"
		::= { swhAccessControlListIPv4Entry 3 }

	swhAccessControlListIPv4IngressPort OBJECT-TYPE
		SYNTAX    DisplayString
		ACCESS    read-write
		STATUS    mandatory
		DESCRIPTION
			"Ingress Port List"
		::= { swhAccessControlListIPv4Entry 4 }

	swhAccessControlListIPv4Action OBJECT-TYPE
		SYNTAX    INTEGER { deny(0), permit(1), mirror(2), redirct(3) }
		ACCESS    read-write
		STATUS    mandatory
		DESCRIPTION
			"Action is deny or permit or mirror or redirct"
		::= { swhAccessControlListIPv4Entry 6 }

	swhAccessControlListIPv4RateLimiter OBJECT-TYPE
		SYNTAX    INTEGER
		ACCESS    read-write
		STATUS    mandatory
		DESCRIPTION
			"Rate Limiter is 16-10485600 Kbps, disable is 0.
			Value drops to upper bound when bound is exceeded (1G port: 1048560, 10G port: 10485600"
		::= { swhAccessControlListIPv4Entry 7 }

	swhAccessControlListIPv4PortCopy OBJECT-TYPE
		SYNTAX    INTEGER
		ACCESS    read-write
		STATUS    mandatory
		DESCRIPTION
			"Port Copy is 1-48, disable is 0"
		::= { swhAccessControlListIPv4Entry 8 }

	swhAccessControlListIPv4Delete OBJECT-TYPE
		SYNTAX    INTEGER { normal(0), delete(1) }
		ACCESS    read-write
		STATUS    mandatory
		DESCRIPTION
			"Delete this Access Control List."
		::= { swhAccessControlListIPv4Entry 10 }

	swhAccessControlListIPv4SourceMACFilter OBJECT-TYPE
		SYNTAX    INTEGER { any(0), specific(1) }
		ACCESS    read-write
		STATUS    mandatory
		DESCRIPTION
			"Source MAC Filter is any or specific"
		::= { swhAccessControlListIPv4Entry 11 }

	swhAccessControlListIPv4SourceMACValue OBJECT-TYPE
		SYNTAX    DisplayString
		ACCESS    read-write
		STATUS    mandatory
		DESCRIPTION
			"Source MAC Value"
		::= { swhAccessControlListIPv4Entry 12 }

	swhAccessControlListIPv4DestinationMACFilter OBJECT-TYPE
		SYNTAX    INTEGER { any(0), specific(1) }
		ACCESS    read-write
		STATUS    mandatory
		DESCRIPTION
			"Destination MAC Filter is any or specific"
		::= { swhAccessControlListIPv4Entry 13 }

	swhAccessControlListIPv4DestinationMACValue OBJECT-TYPE
		SYNTAX    DisplayString
		ACCESS    read-write
		STATUS    mandatory
		DESCRIPTION
			"Destination MAC Value"
		::= { swhAccessControlListIPv4Entry 14 }

	swhAccessControlListIPv4VLANIDFilter OBJECT-TYPE
		SYNTAX    INTEGER { any(0), specific(1) }
		ACCESS    read-write
		STATUS    mandatory
		DESCRIPTION
			"VLAN ID Filter is any or specific"
		::= { swhAccessControlListIPv4Entry 15 }

	swhAccessControlListIPv4VLANID OBJECT-TYPE
		SYNTAX    INTEGER (1..4094)
		ACCESS    read-write
		STATUS    mandatory
		DESCRIPTION
			"VLAN ID is 1-4094"
		::= { swhAccessControlListIPv4Entry 16 }

	swhAccessControlListIPv4EtherTypeFilter OBJECT-TYPE
		SYNTAX    INTEGER { any(0), specific(1) }
		ACCESS    read-write
		STATUS    mandatory
		DESCRIPTION
			"Ether Type Filter is any or specific"
		::= { swhAccessControlListIPv4Entry 18 }

	swhAccessControlListIPv4EthernetTypeValue OBJECT-TYPE
		SYNTAX    DisplayString
		ACCESS    read-write
		STATUS    mandatory
		DESCRIPTION
			"Ethernet Type Value"
		::= { swhAccessControlListIPv4Entry 19 }

	--Date: 141121
	swhAccessControlListIPv4IngressPortFilter OBJECT-TYPE
		SYNTAX    INTEGER { any(0), specific(1) }
		ACCESS    read-write
		STATUS    mandatory
		DESCRIPTION
			"Ingress Port Filter is any or specific"
		::= { swhAccessControlListIPv4Entry 63 }

	swhAccessControlListIPv4SourceMACMask OBJECT-TYPE
		SYNTAX    DisplayString
		ACCESS    read-write
		STATUS    mandatory
		DESCRIPTION
			"Source MAC Mask"
		::= { swhAccessControlListIPv4Entry 64 }

	swhAccessControlListIPv4DestinationMACMask OBJECT-TYPE
		SYNTAX    DisplayString
		ACCESS    read-write
		STATUS    mandatory
		DESCRIPTION
			"Destination MAC Mask"
		::= { swhAccessControlListIPv4Entry 65 }

	swhAccessControlListIPv4TOSTrafficClassFilter OBJECT-TYPE
		SYNTAX    INTEGER { any(0), specific(1) }
		ACCESS    read-write
		STATUS    mandatory
		DESCRIPTION
			"TOS/Traffic Class Filter is any or specific"
		::= { swhAccessControlListIPv4Entry 66 }

	swhAccessControlListIPv4TOSTrafficClass OBJECT-TYPE
		SYNTAX    DisplayString
		ACCESS    read-write
		STATUS    mandatory
		DESCRIPTION
			"TOS/Traffic Class(00-FF)"
		::= { swhAccessControlListIPv4Entry 67 }

	swhAccessControlListIPv4ProtocolNextHeaderFilter OBJECT-TYPE
		SYNTAX    INTEGER { any(0), specific(1) }
		ACCESS    read-write
		STATUS    mandatory
		DESCRIPTION
			"Protocol/Next Header Filter is any or specific"
		::= { swhAccessControlListIPv4Entry 68 }

	swhAccessControlListIPv4ProtocolNextHeader OBJECT-TYPE
		SYNTAX    DisplayString
		ACCESS    read-write
		STATUS    mandatory
		DESCRIPTION
			"Protocol/Next Header(00-FF)"
		::= { swhAccessControlListIPv4Entry 69 }

	swhAccessControlListIPv4IPv4SourceIPFilter OBJECT-TYPE
		SYNTAX    INTEGER { any(0), network(1) }
		ACCESS    read-write
		STATUS    mandatory
		DESCRIPTION
			"IPv4 Source IP Filter"
		::= { swhAccessControlListIPv4Entry 70 }

	swhAccessControlListIPv4IPv4SourceIPAddress OBJECT-TYPE
		SYNTAX    DisplayString
		ACCESS    read-write
		STATUS    mandatory
		DESCRIPTION
			"IPv4 Source IP Address"
		::= { swhAccessControlListIPv4Entry 71 }

	swhAccessControlListIPv4IPv4SourceIPMask OBJECT-TYPE
		SYNTAX    DisplayString
		ACCESS    read-write
		STATUS    mandatory
		DESCRIPTION
			"IPv4 Source IP Mask"
		::= { swhAccessControlListIPv4Entry 72 }

	swhAccessControlListIPv4IPv4DestinationIPFilter OBJECT-TYPE
		SYNTAX    INTEGER { any(0), network(1) }
		ACCESS    read-write
		STATUS    mandatory
		DESCRIPTION
			"IPv4 Source IP Filter"
		::= { swhAccessControlListIPv4Entry 73 }

	swhAccessControlListIPv4IPv4DestinationIPAddress OBJECT-TYPE
		SYNTAX    DisplayString
		ACCESS    read-write
		STATUS    mandatory
		DESCRIPTION
			"IPv4 Destination IP Address"
		::= { swhAccessControlListIPv4Entry 74 }

	swhAccessControlListIPv4IPv4DestinationIPMask OBJECT-TYPE
		SYNTAX    DisplayString
		ACCESS    read-write
		STATUS    mandatory
		DESCRIPTION
			"IPv4 Destination IP Mask"
		::= { swhAccessControlListIPv4Entry 75 }

	swhAccessControlListIPv4TCPUDPSourcePortFilter OBJECT-TYPE
		SYNTAX    INTEGER { any(0), specific(1) }
		ACCESS    read-write
		STATUS    mandatory
		DESCRIPTION
			"TCP/UDP Source Port Filter is any or specific"
		::= { swhAccessControlListIPv4Entry 82 }

	swhAccessControlListIPv4TCPUDPSourcePort OBJECT-TYPE
		SYNTAX    INTEGER
		ACCESS    read-write
		STATUS    mandatory
		DESCRIPTION
			"TCP/UDP Source Port(1-65535)"
		::= { swhAccessControlListIPv4Entry 83 }

	swhAccessControlListIPv4TCPUDPSourcePortMask OBJECT-TYPE
		SYNTAX    DisplayString
		ACCESS    read-write
		STATUS    mandatory
		DESCRIPTION
			"TCP/UDP Source Port Mask(0000-FFFF)"
		::= { swhAccessControlListIPv4Entry 84 }

	swhAccessControlListIPv4TCPUDPDestinationPortFilter OBJECT-TYPE
		SYNTAX    INTEGER { any(0), specific(1) }
		ACCESS    read-write
		STATUS    mandatory
		DESCRIPTION
			"TCP/UDP Destination Port Filter is any or specific"
		::= { swhAccessControlListIPv4Entry 85 }

	swhAccessControlListIPv4TCPUDPDestinationPort OBJECT-TYPE
		SYNTAX    INTEGER
		ACCESS    read-write
		STATUS    mandatory
		DESCRIPTION
			"TCP/UDP Destination Port(1-65535)"
		::= { swhAccessControlListIPv4Entry 86 }

	swhAccessControlListIPv4TCPUDPDestinationPortMask OBJECT-TYPE
		SYNTAX    DisplayString
		ACCESS    read-write
		STATUS    mandatory
		DESCRIPTION
			"TCP/UDP Destination Port Mask(0000-FFFF)"
		::= { swhAccessControlListIPv4Entry 87 }

	swhAccessControlListIPv4Name OBJECT-TYPE
		SYNTAX    DisplayString
		ACCESS    read-write
		STATUS    mandatory
		DESCRIPTION
			"Name"
		::= { swhAccessControlListIPv4Entry 88 }

	swhAccessControlListIPv4Sequence OBJECT-TYPE
		SYNTAX    INTEGER
		ACCESS    read-write
		STATUS    mandatory
		DESCRIPTION
			"Sequence"
		::= { swhAccessControlListIPv4Entry 89 }

	swhAccessControlListIPv4Enable OBJECT-TYPE
		SYNTAX    INTEGER { disable(0), enable(1) }
		ACCESS    read-write
		STATUS    mandatory
		DESCRIPTION
			"Enable or Disable"
		::= { swhAccessControlListIPv4Entry 90 }

	swhAccessControlListIPv4Apply OBJECT-TYPE
		SYNTAX    INTEGER { none(0), apply(1) }
		ACCESS    read-write
		STATUS    mandatory
		DESCRIPTION
			"Apply Access Control List"
		::= { swhAccessControlListIPv4Entry 200 }


-- SwitchManagement(4).ACLConfiguration(65).AccessControlListIPv6(5)

	swhAccessControlListIPv6Table OBJECT-TYPE
		SYNTAX    SEQUENCE OF swhAccessControlListIPv6Entry
		ACCESS    not-accessible
		STATUS    mandatory
		DESCRIPTION
			"Table of Access Control List."
		::= { swhAccessControlListIPv6 1 }

	-- Table Entry
	swhAccessControlListIPv6Entry OBJECT-TYPE
		SYNTAX    swhAccessControlListIPv6Entry
		ACCESS    not-accessible
		STATUS    mandatory
		DESCRIPTION
			"An entry in the table, containing information
			 about Access Control List."
		INDEX    { swhAccessControlListIPv6Index }
		::= { swhAccessControlListIPv6Table 1 }

	swhAccessControlListIPv6Entry ::=
		SEQUENCE {
			swhAccessControlListIPv6Index
				INTEGER,
			swhAccessControlListIPv6Valid
				INTEGER,
			swhAccessControlListIPv6RuleID
				INTEGER,
			swhAccessControlListIPv6Name
				DisplayString,
			swhAccessControlListIPv6Sequence
				INTEGER,
			swhAccessControlListIPv6Enable
				INTEGER,
			swhAccessControlListIPv6IngressPortFilter
			    INTEGER,
			swhAccessControlListIPv6IngressPort
				DisplayString,
			swhAccessControlListIPv6EtherTypeFilter
				INTEGER,
			swhAccessControlListIPv6EthernetTypeValue
				DisplayString,
			swhAccessControlListIPv6VLANIDFilter
				INTEGER,
			swhAccessControlListIPv6VLANID
				INTEGER,
			swhAccessControlListIPv6SourceMACFilter
				INTEGER,
			swhAccessControlListIPv6SourceMACValue
				DisplayString,
			swhAccessControlListIPv6SourceMACMask
				DisplayString,
			swhAccessControlListIPv6DestinationMACFilter
				INTEGER,
			swhAccessControlListIPv6DestinationMACValue
				DisplayString,
			swhAccessControlListIPv6DestinationMACMask
				DisplayString,
			swhAccessControlListIPv6TOSTrafficClassFilter
				INTEGER,
			swhAccessControlListIPv6TOSTrafficClass
				DisplayString,
			swhAccessControlListIPv6ProtocolNextHeaderFilter
				INTEGER,
			swhAccessControlListIPv6ProtocolNextHeader
				DisplayString,
			swhAccessControlListIPv6IPv6SourceIPFilter
				INTEGER,
			swhAccessControlListIPv6IPv6SourceIPAddress
				DisplayString,
			swhAccessControlListIPv6IPv6SourceIPMask
				INTEGER,
			swhAccessControlListIPv6IPv6DestinationIPFilter
				INTEGER,
			swhAccessControlListIPv6IPv6DestinationIPAddress
				DisplayString,
			swhAccessControlListIPv6IPv6DestinationIPMask
				INTEGER,
			swhAccessControlListIPv6TCPUDPSourcePortFilter
				INTEGER,
			swhAccessControlListIPv6TCPUDPSourcePort
				INTEGER,
			swhAccessControlListIPv6TCPUDPSourcePortMask
				DisplayString,
			swhAccessControlListIPv6TCPUDPDestinationPortFilter
				INTEGER,
			swhAccessControlListIPv6TCPUDPDestinationPort
				INTEGER,
			swhAccessControlListIPv6TCPUDPDestinationPortMask
				DisplayString,
			swhAccessControlListIPv6Action
				INTEGER,
			swhAccessControlListIPv6PortCopy
				INTEGER,
			swhAccessControlListIPv6RateLimiter
				INTEGER,
			swhAccessControlListIPv6Apply
				INTEGER,
			swhAccessControlListIPv6Delete
				INTEGER
		}

	swhAccessControlListIPv6Index OBJECT-TYPE
		SYNTAX    INTEGER (0..2147483647)
		ACCESS    not-accessible
		STATUS    mandatory
		DESCRIPTION
			"A unique value for Access Control List."
		::= { swhAccessControlListIPv6Entry 1 }

	swhAccessControlListIPv6Valid OBJECT-TYPE
		SYNTAX    INTEGER { valid(1), invalid(0) }
		ACCESS    read-only
		STATUS    mandatory
		DESCRIPTION
			"Valid"
		::= { swhAccessControlListIPv6Entry 2 }

	swhAccessControlListIPv6RuleID OBJECT-TYPE
		SYNTAX    INTEGER (1..110)
		ACCESS    read-only
		STATUS    mandatory
		DESCRIPTION
			"Rule ID (1-192)"
		::= { swhAccessControlListIPv6Entry 3 }

	swhAccessControlListIPv6IngressPort OBJECT-TYPE
		SYNTAX    DisplayString
		ACCESS    read-write
		STATUS    mandatory
		DESCRIPTION
			"Ingress Port List"
		::= { swhAccessControlListIPv6Entry 4 }

	swhAccessControlListIPv6Action OBJECT-TYPE
		SYNTAX    INTEGER { deny(0), permit(1), mirror(2), redirct(3) }
		ACCESS    read-write
		STATUS    mandatory
		DESCRIPTION
			"Action is deny or permit or mirror or redirct"
		::= { swhAccessControlListIPv6Entry 6 }

	swhAccessControlListIPv6RateLimiter OBJECT-TYPE
		SYNTAX    INTEGER
		ACCESS    read-write
		STATUS    mandatory
		DESCRIPTION
			"Rate Limiter is 16-10485600 Kbps, disable is 0.
			Value drops to upper bound when bound is exceeded (1G port: 1048560, 10G port: 10485600"
		::= { swhAccessControlListIPv6Entry 7 }

	swhAccessControlListIPv6PortCopy OBJECT-TYPE
		SYNTAX    INTEGER
		ACCESS    read-write
		STATUS    mandatory
		DESCRIPTION
			"Port Copy is 1-48, disable is 0"
		::= { swhAccessControlListIPv6Entry 8 }

	swhAccessControlListIPv6Delete OBJECT-TYPE
		SYNTAX    INTEGER { normal(0), delete(1) }
		ACCESS    read-write
		STATUS    mandatory
		DESCRIPTION
			"Delete this Access Control List."
		::= { swhAccessControlListIPv6Entry 10 }

	swhAccessControlListIPv6SourceMACFilter OBJECT-TYPE
		SYNTAX    INTEGER { any(0), specific(1) }
		ACCESS    read-write
		STATUS    mandatory
		DESCRIPTION
			"Source MAC Filter is any or specific"
		::= { swhAccessControlListIPv6Entry 11 }

	swhAccessControlListIPv6SourceMACValue OBJECT-TYPE
		SYNTAX    DisplayString
		ACCESS    read-write
		STATUS    mandatory
		DESCRIPTION
			"Source MAC Value"
		::= { swhAccessControlListIPv6Entry 12 }

	swhAccessControlListIPv6DestinationMACFilter OBJECT-TYPE
		SYNTAX    INTEGER { any(0), specific(1) }
		ACCESS    read-write
		STATUS    mandatory
		DESCRIPTION
			"Destination MAC Filter is any or specific"
		::= { swhAccessControlListIPv6Entry 13 }

	swhAccessControlListIPv6DestinationMACValue OBJECT-TYPE
		SYNTAX    DisplayString
		ACCESS    read-write
		STATUS    mandatory
		DESCRIPTION
			"Destination MAC Value"
		::= { swhAccessControlListIPv6Entry 14 }

	swhAccessControlListIPv6VLANIDFilter OBJECT-TYPE
		SYNTAX    INTEGER { any(0), specific(1) }
		ACCESS    read-write
		STATUS    mandatory
		DESCRIPTION
			"VLAN ID Filter is any or specific"
		::= { swhAccessControlListIPv6Entry 15 }

	swhAccessControlListIPv6VLANID OBJECT-TYPE
		SYNTAX    INTEGER (1..4094)
		ACCESS    read-write
		STATUS    mandatory
		DESCRIPTION
			"VLAN ID is 1-4094"
		::= { swhAccessControlListIPv6Entry 16 }

	swhAccessControlListIPv6EtherTypeFilter OBJECT-TYPE
		SYNTAX    INTEGER { any(0), specific(1) }
		ACCESS    read-write
		STATUS    mandatory
		DESCRIPTION
			"Ether Type Filter is any or specific"
		::= { swhAccessControlListIPv6Entry 18 }

	swhAccessControlListIPv6EthernetTypeValue OBJECT-TYPE
		SYNTAX    DisplayString
		ACCESS    read-write
		STATUS    mandatory
		DESCRIPTION
			"Ethernet Type Value"
		::= { swhAccessControlListIPv6Entry 19 }

	--Date: 141121
	swhAccessControlListIPv6IngressPortFilter OBJECT-TYPE
		SYNTAX    INTEGER { any(0), specific(1) }
		ACCESS    read-write
		STATUS    mandatory
		DESCRIPTION
			"Ingress Port Filter is any or specific"
		::= { swhAccessControlListIPv6Entry 63 }

	swhAccessControlListIPv6SourceMACMask OBJECT-TYPE
		SYNTAX    DisplayString
		ACCESS    read-write
		STATUS    mandatory
		DESCRIPTION
			"Source MAC Mask"
		::= { swhAccessControlListIPv6Entry 64 }

	swhAccessControlListIPv6DestinationMACMask OBJECT-TYPE
		SYNTAX    DisplayString
		ACCESS    read-write
		STATUS    mandatory
		DESCRIPTION
			"Destination MAC Mask"
		::= { swhAccessControlListIPv6Entry 65 }

	swhAccessControlListIPv6TOSTrafficClassFilter OBJECT-TYPE
		SYNTAX    INTEGER { any(0), specific(1) }
		ACCESS    read-write
		STATUS    mandatory
		DESCRIPTION
			"TOS/Traffic Class Filter is any or specific"
		::= { swhAccessControlListIPv6Entry 66 }

	swhAccessControlListIPv6TOSTrafficClass OBJECT-TYPE
		SYNTAX    DisplayString
		ACCESS    read-write
		STATUS    mandatory
		DESCRIPTION
			"TOS/Traffic Class(00-FF)"
		::= { swhAccessControlListIPv6Entry 67 }

	swhAccessControlListIPv6ProtocolNextHeaderFilter OBJECT-TYPE
		SYNTAX    INTEGER { any(0), specific(1) }
		ACCESS    read-write
		STATUS    mandatory
		DESCRIPTION
			"Protocol/Next Header Filter is any or specific"
		::= { swhAccessControlListIPv6Entry 68 }

	swhAccessControlListIPv6ProtocolNextHeader OBJECT-TYPE
		SYNTAX    DisplayString
		ACCESS    read-write
		STATUS    mandatory
		DESCRIPTION
			"Protocol/Next Header(00-FF)"
		::= { swhAccessControlListIPv6Entry 69 }

	swhAccessControlListIPv6IPv6SourceIPFilter OBJECT-TYPE
		SYNTAX    INTEGER { any(0), network(1) }
		ACCESS    read-write
		STATUS    mandatory
		DESCRIPTION
			"IPv6 Source IP Filter"
		::= { swhAccessControlListIPv6Entry 76 }

	swhAccessControlListIPv6IPv6SourceIPAddress OBJECT-TYPE
		SYNTAX    DisplayString
		ACCESS    read-write
		STATUS    mandatory
		DESCRIPTION
			"IPv6 Source IP Address"
		::= { swhAccessControlListIPv6Entry 77 }

	swhAccessControlListIPv6IPv6SourceIPMask OBJECT-TYPE
		SYNTAX    INTEGER
		ACCESS    read-write
		STATUS    mandatory
		DESCRIPTION
			"IPv6 Source IP Mask(1-255)"
		::= { swhAccessControlListIPv6Entry 78 }

	swhAccessControlListIPv6IPv6DestinationIPFilter OBJECT-TYPE
		SYNTAX    INTEGER { any(0), network(1) }
		ACCESS    read-write
		STATUS    mandatory
		DESCRIPTION
			"IPv6 Source IP Filter"
		::= { swhAccessControlListIPv6Entry 79 }

	swhAccessControlListIPv6IPv6DestinationIPAddress OBJECT-TYPE
		SYNTAX    DisplayString
		ACCESS    read-write
		STATUS    mandatory
		DESCRIPTION
			"IPv6 Destination IP Address"
		::= { swhAccessControlListIPv6Entry 80 }

	swhAccessControlListIPv6IPv6DestinationIPMask OBJECT-TYPE
		SYNTAX    INTEGER
		ACCESS    read-write
		STATUS    mandatory
		DESCRIPTION
			"IPv6 Destination IP Mask(1-255)"
		::= { swhAccessControlListIPv6Entry 81 }

	swhAccessControlListIPv6TCPUDPSourcePortFilter OBJECT-TYPE
		SYNTAX    INTEGER { any(0), specific(1) }
		ACCESS    read-write
		STATUS    mandatory
		DESCRIPTION
			"TCP/UDP Source Port Filter is any or specific"
		::= { swhAccessControlListIPv6Entry 82 }

	swhAccessControlListIPv6TCPUDPSourcePort OBJECT-TYPE
		SYNTAX    INTEGER
		ACCESS    read-write
		STATUS    mandatory
		DESCRIPTION
			"TCP/UDP Source Port(1-65535)"
		::= { swhAccessControlListIPv6Entry 83 }

	swhAccessControlListIPv6TCPUDPSourcePortMask OBJECT-TYPE
		SYNTAX    DisplayString
		ACCESS    read-write
		STATUS    mandatory
		DESCRIPTION
			"TCP/UDP Source Port Mask(0000-FFFF)"
		::= { swhAccessControlListIPv6Entry 84 }

	swhAccessControlListIPv6TCPUDPDestinationPortFilter OBJECT-TYPE
		SYNTAX    INTEGER { any(0), specific(1) }
		ACCESS    read-write
		STATUS    mandatory
		DESCRIPTION
			"TCP/UDP Destination Port Filter is any or specific"
		::= { swhAccessControlListIPv6Entry 85 }

	swhAccessControlListIPv6TCPUDPDestinationPort OBJECT-TYPE
		SYNTAX    INTEGER
		ACCESS    read-write
		STATUS    mandatory
		DESCRIPTION
			"TCP/UDP Destination Port(1-65535)"
		::= { swhAccessControlListIPv6Entry 86 }

	swhAccessControlListIPv6TCPUDPDestinationPortMask OBJECT-TYPE
		SYNTAX    DisplayString
		ACCESS    read-write
		STATUS    mandatory
		DESCRIPTION
			"TCP/UDP Destination Port Mask(0000-FFFF)"
		::= { swhAccessControlListIPv6Entry 87 }

	swhAccessControlListIPv6Name OBJECT-TYPE
		SYNTAX    DisplayString
		ACCESS    read-write
		STATUS    mandatory
		DESCRIPTION
			"Name"
		::= { swhAccessControlListIPv6Entry 88 }

	swhAccessControlListIPv6Sequence OBJECT-TYPE
		SYNTAX    INTEGER
		ACCESS    read-write
		STATUS    mandatory
		DESCRIPTION
			"Sequence"
		::= { swhAccessControlListIPv6Entry 89 }

	swhAccessControlListIPv6Enable OBJECT-TYPE
		SYNTAX    INTEGER { disable(0), enable(1) }
		ACCESS    read-write
		STATUS    mandatory
		DESCRIPTION
			"Enable or Disable"
		::= { swhAccessControlListIPv6Entry 90 }

	swhAccessControlListIPv6Apply OBJECT-TYPE
		SYNTAX    INTEGER { none(0), apply(1) }
		ACCESS    read-write
		STATUS    mandatory
		DESCRIPTION
			"Apply Access Control List"
		::= { swhAccessControlListIPv6Entry 200 }


-- SwitchManagement(4).StaticMulticastConfiguration(70).MulticastTable(1)

	swhMulticastTable OBJECT-TYPE
		SYNTAX    SEQUENCE OF SwhMulticastEntry
		ACCESS    not-accessible
		STATUS    mandatory
		DESCRIPTION
			"Table of Multicast."
		::= { swhStaticMulticastConfiguration 1 }

	-- Table Entry
	swhMulticastEntry OBJECT-TYPE
		SYNTAX    SwhMulticastEntry
		ACCESS    not-accessible
		STATUS    mandatory
		DESCRIPTION
			"An entry in the table, containing information
			about Multicast."
		INDEX    { swhMulticastIndex }
		::= { swhMulticastTable 1 }

	SwhMulticastEntry ::=
		SEQUENCE {
			swhMulticastIndex
				INTEGER,
			swhMulticastValid
				INTEGER,
			swhMulticastIPAddress
				IpAddress,
			swhMulticastIPv6Address
				DisplayString,
			swhMulticastVLANID
				INTEGER,	
			swhMulticastForwardingPort
				INTEGER,
			swhMulticastDelete
				INTEGER
		}

	swhMulticastIndex OBJECT-TYPE
		SYNTAX    INTEGER (0..2147483647)
		ACCESS    not-accessible
		STATUS    mandatory
		DESCRIPTION
			"A unique value for each Segment."
		::= { swhMulticastEntry 1 }

	swhMulticastValid OBJECT-TYPE
		SYNTAX    INTEGER { invalid(0), valid(1) }
		ACCESS    read-only
		STATUS    mandatory
		DESCRIPTION
			"This group setting is valid or invalid."
		::= { swhMulticastEntry 2 }

	swhMulticastIPAddress OBJECT-TYPE
		SYNTAX    IpAddress
		ACCESS    read-write
		STATUS    mandatory
		DESCRIPTION
			"IP Address 224.0.1.0-239.255.255.255"
		::= { swhMulticastEntry 3 }

	swhMulticastVLANID OBJECT-TYPE
		SYNTAX    INTEGER (1..4094)
		ACCESS    read-write
		STATUS    mandatory
		DESCRIPTION
			"VLAN ID (1-4094)"
		::= { swhMulticastEntry 6 }

	swhMulticastForwardingPort OBJECT-TYPE
		SYNTAX    INTEGER { port01(0),
		                    port02(1),
		                    port03(2),
		                    port04(3),
		                    port05(4),
		                    port06(5)
		                    }
		ACCESS    read-write
		STATUS    mandatory
		DESCRIPTION
			"Forwarding Port"
		::= { swhMulticastEntry 7 }

	swhMulticastDelete OBJECT-TYPE
		SYNTAX    INTEGER { normal(0), delete(1) }
		ACCESS    read-write
		STATUS    mandatory
		DESCRIPTION
			"Delete this Multicast."
		::= { swhMulticastEntry 10 }

	swhMulticastIPv6Address OBJECT-TYPE
		SYNTAX    DisplayString
		ACCESS    read-write
		STATUS    mandatory
		DESCRIPTION
			"IPv6 Address FF00::/8"
		::= { swhMulticastEntry 11 }


-- SwitchManagement(4).MVRConfiguration(75)


-- SwitchManagement(4).MVRConfiguration(75).MVRSettings(1)


-- SwitchManagement(4).MVRConfiguration(75).MVRGroups(2)


-- SwitchManagement(4).SecurityConfiguration(80)

	swhDHCPOpt82Settings
		OBJECT IDENTIFIER ::= { swhSecurityConfiguration 1 }
	swhDHCPOpt82Configuration
		OBJECT IDENTIFIER ::= { swhSecurityConfiguration 7 }
	swhIPSourceGuardSettings
		OBJECT IDENTIFIER ::= { swhSecurityConfiguration 2 }
	swhPortIsolationConfiguration
		OBJECT IDENTIFIER ::= { swhSecurityConfiguration 13 }
	swhDHCPSnooping
		OBJECT IDENTIFIER ::= { swhSecurityConfiguration 3 }
	swhStaticIPTableConfiguration
		OBJECT IDENTIFIER ::= { swhSecurityConfiguration 4 }
	swhStormControl
		OBJECT IDENTIFIER ::= { swhSecurityConfiguration 12 }
--	swhMacLimiters
--		OBJECT IDENTIFIER ::= { swhSecurityConfiguration 11 }
	swhPortLinkupDelay
		OBJECT IDENTIFIER ::= { swhSecurityConfiguration 15 }
	swhPortLinkFlap
		OBJECT IDENTIFIER ::= { swhSecurityConfiguration 16 }


-- SwitchManagement(4).SecurityConfiguration(80).DHCPOpt82Settings(1)

	swhSecurityConfigDHCPOpt82RelayAgent OBJECT-TYPE
		SYNTAX    INTEGER { disable(0), enable(1) }
		ACCESS    read-write
		STATUS    mandatory
		DESCRIPTION
			"enable DHCP Opt82 Relay Agent, The Opt82 Port has to be used."
		::= { swhDHCPOpt82Settings 1 }

	swhSecurityConfigRemoteID OBJECT-TYPE
		SYNTAX    DisplayString
		ACCESS    read-only
		STATUS    mandatory
		DESCRIPTION
			"Monitor Remote ID"
		::= { swhDHCPOpt82Settings 2 }

	swhSecurityConfigDHCPOpt82PortTable OBJECT-TYPE
		SYNTAX    SEQUENCE OF SwhSecurityConfigDHCPOpt82PortTableEntry
		ACCESS    not-accessible
		STATUS    mandatory
		DESCRIPTION
			"Table of DHCP Server Trust Port."
		::= { swhDHCPOpt82Settings 3 }

	-- Table Entry
	swhSecurityConfigDHCPOpt82PortTableEntry OBJECT-TYPE
		SYNTAX    SwhSecurityConfigDHCPOpt82PortTableEntry
		ACCESS    not-accessible
		STATUS    mandatory
		DESCRIPTION
			"An entry in the table, containing information
			about DHCP Opt82 Port."
		INDEX     { swhDHCPOpt82PortIndex }
		::= { swhSecurityConfigDHCPOpt82PortTable 1 }

	SwhSecurityConfigDHCPOpt82PortTableEntry ::=
		SEQUENCE {
			swhDHCPOpt82PortIndex
				INTEGER,
			swhDHCPOpt82PortOpt82Port
				INTEGER,
			swhDHCPOpt82PortTrustPort
				INTEGER
		}

	swhDHCPOpt82PortIndex OBJECT-TYPE
		SYNTAX    INTEGER (0..2147483647)
		ACCESS    not-accessible
		STATUS    mandatory
		DESCRIPTION
			"A unique value for each port."
		::= { swhSecurityConfigDHCPOpt82PortTableEntry 1 }

	swhDHCPOpt82PortOpt82Port OBJECT-TYPE
		SYNTAX    INTEGER { b(0), v(1) }
		ACCESS    read-write
		STATUS    mandatory
		DESCRIPTION
			"b:Blocked  v:Member"
		::= { swhSecurityConfigDHCPOpt82PortTableEntry 2 }

	swhDHCPOpt82PortTrustPort OBJECT-TYPE
		SYNTAX    INTEGER { b(0), v(1) }
		ACCESS    read-write
		STATUS    mandatory
		DESCRIPTION
			"b:Blocked  v:Member"
		::= { swhSecurityConfigDHCPOpt82PortTableEntry 3 }


-- SwitchManagement(4).SecurityConfiguration(80).IPSourceGuardSettings(2)

	swhIPSourceGuardSettingsPort1 OBJECT-TYPE
		SYNTAX    INTEGER { fix-ip(0), dhcp(1), unlimited(2) }
		ACCESS    read-write
		STATUS    mandatory
		DESCRIPTION
			"Port1 State is fix-ip, dhcp or unlimited."
		::= { swhIPSourceGuardSettings 1 }

	swhIPSourceGuardSettingsPort2 OBJECT-TYPE
		SYNTAX    INTEGER { fix-ip(0), dhcp(1), unlimited(2) }
		ACCESS    read-write
		STATUS    mandatory
		DESCRIPTION
			"Port2 State is fix-ip, dhcp or unlimited."
		::= { swhIPSourceGuardSettings 2 }

	swhIPSourceGuardSettingsPort3 OBJECT-TYPE
		SYNTAX    INTEGER { fix-ip(0), dhcp(1), unlimited(2) }
		ACCESS    read-write
		STATUS    mandatory
		DESCRIPTION
			"Port3 State is fix-ip, dhcp or unlimited."
		::= { swhIPSourceGuardSettings 3 }

	swhIPSourceGuardSettingsPort4 OBJECT-TYPE
		SYNTAX    INTEGER { fix-ip(0), dhcp(1), unlimited(2) }
		ACCESS    read-write
		STATUS    mandatory
		DESCRIPTION
			"Port4 State is fix-ip, dhcp or unlimited."
		::= { swhIPSourceGuardSettings 4 }

	swhIPSourceGuardSettingsPort5 OBJECT-TYPE
		SYNTAX    INTEGER { fix-ip(0), dhcp(1), unlimited(2) }
		ACCESS    read-write
		STATUS    mandatory
		DESCRIPTION
			"Port5 State is fix-ip, dhcp or unlimited."
		::= { swhIPSourceGuardSettings 5 }

	swhIPSourceGuardSettingsPort6 OBJECT-TYPE
		SYNTAX    INTEGER { fix-ip(0), dhcp(1), unlimited(2) }
		ACCESS    read-write
		STATUS    mandatory
		DESCRIPTION
			"Port6 State is fix-ip, dhcp or unlimited."
		::= { swhIPSourceGuardSettings 6 }


-- SwitchManagement(4).SecurityConfiguration(80).FilterConfiguration(3)

	swhFilterConfigDHCPSnooping OBJECT-TYPE
		SYNTAX    INTEGER { disable(0), enable(1) }
		ACCESS    read-write
		STATUS    mandatory
		DESCRIPTION
			"Enable or disable DHCP Snooping.
			 When DHCP Snooping is enable, ARP/IPv4 filter will also be enable simultaneously"
		::= { swhDHCPSnooping 1 }

	swhFilterConfigDefaultDHCPInitiatedTime OBJECT-TYPE
		SYNTAX    INTEGER (0..9999)
		ACCESS    read-write
		STATUS    mandatory
		DESCRIPTION
			"Default DHCP Initiated Time. 0-9999"
		::= { swhDHCPSnooping 2 }

	swhFilterConfigDefaultDHCPLeasedTime OBJECT-TYPE
		SYNTAX    INTEGER (180..259200)
		ACCESS    read-write
		STATUS    mandatory
		DESCRIPTION
			"Default DHCP Leased Time. 180-259200"
		::= { swhDHCPSnooping 3 }

--	swhFilterConfigPortIsolation OBJECT-TYPE
--		SYNTAX    INTEGER { disable(0), enable(1) }
--		ACCESS    read-write
--		STATUS    mandatory
--		DESCRIPTION
--			"Enable or disable Port Isolation"
--		::= { swhDHCPSnooping 4 }

--	swhFilterConfigIPv6 OBJECT-TYPE
--		SYNTAX    INTEGER { disable(0), enable(1) }
--		ACCESS    read-write
--		STATUS    mandatory
--		DESCRIPTION
--			"Enable or disable IPv6 auto discovery / DHCPv6"
--		::= { swhDHCPSnooping 5 }

--	swhFilterConfigUPnP OBJECT-TYPE
--		SYNTAX    INTEGER { disable(0), enable(1) }
--		ACCESS    read-write
--		STATUS    mandatory
--		DESCRIPTION
--			"Enable or disable UPnP"
--		::= { swhDHCPSnooping 6 }


-- SwitchManagement(4).SecurityConfiguration(80).FilterConfiguration(3).DHCPServerTrustPort(7)

	swhSecurityDHCPServerTrustPort
		OBJECT IDENTIFIER ::= { swhDHCPSnooping 7 }


-- SwitchManagement(4).SecurityConfiguration(80).FilterConfiguration(3).DHCPServerTrustPort(7).DHCPServerTable(1)

	swhSecurityDHCPServerTable OBJECT-TYPE
		SYNTAX    SEQUENCE OF SwhSecurityDHCPServerTableEntry
		ACCESS    not-accessible
		STATUS    mandatory
		DESCRIPTION
			"Table of DHCP Server Trust Port."
		::= { swhSecurityDHCPServerTrustPort 1 }

	-- Table Entry
	swhSecurityDHCPServerTableEntry OBJECT-TYPE
		SYNTAX    SwhSecurityDHCPServerTableEntry
		ACCESS    not-accessible
		STATUS    mandatory
		DESCRIPTION
			"An entry in the table, containing information
			about DHCP Server Trust Port."
		INDEX     { swhSecurityDHCPServerTableIndex }
		::= { swhSecurityDHCPServerTable 1 }

	SwhSecurityDHCPServerTableEntry ::=
		SEQUENCE {
			swhSecurityDHCPServerTableIndex
				INTEGER,
			swhSecurityDHCPServerTableState
				INTEGER
		}

	swhSecurityDHCPServerTableIndex OBJECT-TYPE
		SYNTAX    INTEGER (0..2147483647)
		ACCESS    not-accessible
		STATUS    mandatory
		DESCRIPTION
			"A unique value for each port."
		::= { swhSecurityDHCPServerTableEntry 1 }

	swhSecurityDHCPServerTableState OBJECT-TYPE
		SYNTAX    INTEGER { disable(0), enable(1) }
		ACCESS    read-write
		STATUS    mandatory
		DESCRIPTION
			"enable or disable port"
		::= { swhSecurityDHCPServerTableEntry 2 }


-- SwitchManagement(4).SecurityConfiguration(80).FilterConfiguration(3).DHCPServerTrustIP(8)

	swhSecurityDHCPServerTrustIP
		OBJECT IDENTIFIER ::= { swhDHCPSnooping 8 }


-- SwitchManagement(4).SecurityConfiguration(80).FilterConfiguration(3).DHCPServerTrustIP(8).DHCPServerIP(1)

	swhSecurityDHCPServerIP OBJECT-TYPE
		SYNTAX    INTEGER { disable(0), enable(1) }
		ACCESS    read-write
		STATUS    mandatory
		DESCRIPTION
			"Security IP enable or disable"
		::= { swhSecurityDHCPServerTrustIP 1 }


-- SwitchManagement(4).SecurityConfiguration(80).FilterConfiguration(3).DHCPServerTrustIP(8).DHCPServerIPTable(2)

	swhSecurityDHCPServerIPTable OBJECT-TYPE
		SYNTAX    SEQUENCE OF SwhSecurityDHCPServerIPEntry
		ACCESS    not-accessible
		STATUS    mandatory
		DESCRIPTION
			"Table of Security IP information."
		::= { swhSecurityDHCPServerTrustIP 2 }

	-- Table Entry
	swhSecurityDHCPServerIPEntry OBJECT-TYPE
		SYNTAX    SwhSecurityDHCPServerIPEntry
		ACCESS    not-accessible
		STATUS    mandatory
		DESCRIPTION
			"An entry in the table, containing information
			 about SNMP agent.
			 Only Administrator can read this table"
		INDEX    { swhSecurityDHCPServerIPIndex }
		::= { swhSecurityDHCPServerIPTable 1 }

	SwhSecurityDHCPServerIPEntry ::=
		SEQUENCE {
			swhSecurityDHCPServerIPIndex
				INTEGER,
			swhSecurityDHCPServerIPIPAddress
				DisplayString,
			swhSecurityDHCPServerIPIPv6Address
				DisplayString,
			swhSecurityDHCPServerIPDelete
				INTEGER
		}

	swhSecurityDHCPServerIPIndex OBJECT-TYPE
		SYNTAX    INTEGER (0..2147483647)
		ACCESS    not-accessible
		STATUS    mandatory
		DESCRIPTION
			"Security IP index"
		::= { swhSecurityDHCPServerIPEntry 1 }

	swhSecurityDHCPServerIPIPAddress OBJECT-TYPE
		SYNTAX    DisplayString
		ACCESS    read-write
		STATUS    mandatory
		DESCRIPTION
			"Security IPv4 Address"
		::= { swhSecurityDHCPServerIPEntry 4 }

	swhSecurityDHCPServerIPIPv6Address OBJECT-TYPE
		SYNTAX    DisplayString
		ACCESS    read-write
		STATUS    mandatory
		DESCRIPTION
			"Security IPv6 Address"
		::= { swhSecurityDHCPServerIPEntry 5 }

	swhSecurityDHCPServerIPDelete OBJECT-TYPE
		SYNTAX    INTEGER { normal(0), delete(1) }
		ACCESS    read-write
		STATUS    mandatory
		DESCRIPTION
			"Delete this entry."
		::= { swhSecurityDHCPServerIPEntry 10 }


-- SwitchManagement(4).SecurityConfiguration(80).StaticIPTableConfiguration(4).StaticIPTable(1)

	swhStaticIPTable OBJECT-TYPE
		SYNTAX    SEQUENCE OF SwhStaticIPTableEntry
		ACCESS    not-accessible
		STATUS    mandatory
		DESCRIPTION
			"Table of State IP."
		::= { swhStaticIPTableConfiguration 1 }

	-- Table Entry
	swhStaticIPTableEntry OBJECT-TYPE
		SYNTAX    SwhStaticIPTableEntry
		ACCESS    not-accessible
		STATUS    mandatory
		DESCRIPTION
			"An entry in the table, containing information
			about State IP."
		INDEX     { swhStaticIPTableIndex }
		::= { swhStaticIPTable 1 }

	SwhStaticIPTableEntry ::=
		SEQUENCE {
			swhStaticIPTableIndex
				INTEGER,
			swhStaticIPTableValid
				INTEGER,
			swhStaticIPTableIPAddress
				IpAddress,
			swhStaticIPTableIPv6Address
				DisplayString,
--			swhStaticIPTableMaskAddress
--				IpAddress,
			swhStaticIPTableVLANID
				INTEGER,
			swhStaticIPTablePort
				INTEGER,
			swhStaticIPTableDelete
				INTEGER
		}

	swhStaticIPTableIndex OBJECT-TYPE
		SYNTAX    INTEGER (0..2147483647)
		ACCESS    not-accessible
		STATUS    mandatory
		DESCRIPTION
			"A unique value for each Segment."
		::= { swhStaticIPTableEntry 1 }

	swhStaticIPTableValid OBJECT-TYPE
		SYNTAX    INTEGER { invalid(0), valid(1) }
		ACCESS    read-only
		STATUS    mandatory
		DESCRIPTION
			"This group setting is valid or invalid."
		::= { swhStaticIPTableEntry 2 }

	swhStaticIPTableIPAddress OBJECT-TYPE
		SYNTAX    IpAddress
		ACCESS    read-write
		STATUS    mandatory
		DESCRIPTION
			"IP Address"
		::= { swhStaticIPTableEntry 3 }

--	swhStaticIPTableMaskAddress OBJECT-TYPE
--		SYNTAX    IpAddress
--		ACCESS    read-write
--		STATUS    mandatory
--		DESCRIPTION
--			"Mask Address"
--		::= { swhStaticIPTableEntry 4 }

	swhStaticIPTableVLANID OBJECT-TYPE
		SYNTAX    INTEGER (1..4094)
		ACCESS    read-write
		STATUS    mandatory
		DESCRIPTION
			"VLAN ID (1-4094)"
		::= { swhStaticIPTableEntry 5 }

	swhStaticIPTablePort OBJECT-TYPE
		SYNTAX    INTEGER { port01(0),
		                    port02(1),
		                    port03(2),
		                    port04(3),
		                    port05(4),
		                    port06(5)
		                    }
		ACCESS    read-write
		STATUS    mandatory
		DESCRIPTION
			"Port Number"
		::= { swhStaticIPTableEntry 6 }

	swhStaticIPTableDelete OBJECT-TYPE
		SYNTAX    INTEGER { normal(0), delete(1) }
		ACCESS    read-write
		STATUS    mandatory
		DESCRIPTION
			"Delete this State IP."
		::= { swhStaticIPTableEntry 7 }

	swhStaticIPTableIPv6Address OBJECT-TYPE
		SYNTAX    DisplayString
		ACCESS    read-write
		STATUS    mandatory
		DESCRIPTION
			"IPv6 Address"
		::= { swhStaticIPTableEntry 8 }


-- SwitchManagement(4).SecurityConfiguration(80).AntiBcastConfiguration(6)


-- SwitchManagement(4).SecurityConfiguration(80).DHCPOpt82Configuration(7)

	swhDHCPOpt82CircuitIDPortList OBJECT-TYPE
		SYNTAX    DisplayString (SIZE (0..255))
		ACCESS    read-write
		STATUS    mandatory
		DESCRIPTION
			"DHCP Opt82 Circuit-ID Port List."
		::= { swhDHCPOpt82Configuration 2 }

	swhDHCPOpt82CircuitIDFormattedPortList OBJECT-TYPE
		SYNTAX    DisplayString (SIZE (0..255))
		ACCESS    read-write
		STATUS    mandatory
		DESCRIPTION
			"DHCP Opt82 Circuit-ID Formatted Port List."
		::= { swhDHCPOpt82Configuration 6 }

	swhDHCPOpt82RemoteIDEnable OBJECT-TYPE
		SYNTAX    INTEGER { disable(0), enable(1) }
		ACCESS    read-write
		STATUS    mandatory
		DESCRIPTION
			"Enable or disable DHCP Opt82 Remote-ID"
		::= { swhDHCPOpt82Configuration 4 }

	swhDHCPOpt82RemoteIDFormattedEnable OBJECT-TYPE
		SYNTAX    INTEGER { disable(0), enable(1) }
		ACCESS    read-write
		STATUS    mandatory
		DESCRIPTION
			"Enable or disable DHCP Opt82 Remote-ID Formatted"
		::= { swhDHCPOpt82Configuration 7 }

	swhDHCPOpt82RemoteID OBJECT-TYPE
		SYNTAX    DisplayString
		ACCESS    read-write
		STATUS    mandatory
		DESCRIPTION
			"DHCP Opt82 Remote-ID"
		::= { swhDHCPOpt82Configuration 5 }


-- SwitchManagement(4).SecurityConfiguration(80).DHCPOpt82Configuration(7).swhDHCPOpt82CircuitIDTable(3)

	swhDHCPOpt82CircuitIDTable OBJECT-TYPE
		SYNTAX    SEQUENCE OF SwhDHCPOpt82CircuitIDTableEntry
		ACCESS    not-accessible
		STATUS    mandatory
		DESCRIPTION
			"Table of DHCP Opt82 Circuit-ID."
		::= { swhDHCPOpt82Configuration 3 }

	-- Table Entry
	swhDHCPOpt82CircuitIDTableEntry OBJECT-TYPE
		SYNTAX    SwhDHCPOpt82CircuitIDTableEntry
		ACCESS    not-accessible
		STATUS    mandatory
		DESCRIPTION
			"An entry in the table, containing information
			about DHCP Opt82 Circuit-ID."
		INDEX     { swhDHCPOpt82CircuitIDTableIndex }
		::= { swhDHCPOpt82CircuitIDTable 1 }

	SwhDHCPOpt82CircuitIDTableEntry ::=
		SEQUENCE {
			swhDHCPOpt82CircuitIDTableIndex
				INTEGER,
			swhDHCPOpt82CircuitIDTableCircuitID
				DisplayString,
			swhDHCPOpt82CircuitIDTableDelete
				INTEGER
		}

	swhDHCPOpt82CircuitIDTableIndex OBJECT-TYPE
		SYNTAX    INTEGER (0..2147483647)
		ACCESS    not-accessible
		STATUS    mandatory
		DESCRIPTION
			"A unique value for each port."
		::= { swhDHCPOpt82CircuitIDTableEntry 1 }

	swhDHCPOpt82CircuitIDTableCircuitID OBJECT-TYPE
		SYNTAX    DisplayString
		ACCESS    read-write
		STATUS    mandatory
		DESCRIPTION
			"Circuit-ID"
		::= { swhDHCPOpt82CircuitIDTableEntry 3 }

	swhDHCPOpt82CircuitIDTableDelete OBJECT-TYPE
		SYNTAX    INTEGER { normal(0), delete(1) }
		ACCESS    read-write
		STATUS    mandatory
		DESCRIPTION
			"Delete this Circuit-ID."
		::= { swhDHCPOpt82CircuitIDTableEntry 5 }


-- SwitchManagement(4).SecurityConfiguration(80).DHCPRecordPortSettings(8)


-- SwitchManagement(4).SecurityConfiguration(80).MacLimiters(11)
--
--	swhMacLimitersEnable OBJECT-TYPE
--		SYNTAX    INTEGER { disable(0), enable(1) }
--		ACCESS    read-write
--		STATUS    mandatory
--		DESCRIPTION
--			""
--		::= { swhMacLimiters 1 }
--
--	swhMacLimitersThresholdInterval OBJECT-TYPE
--		SYNTAX    INTEGER (120..86400)
--		ACCESS    read-write
--		STATUS    mandatory
--		DESCRIPTION
--			"Threshold Interval"
--		::= { swhMacLimiters 3 }
--
--
-- SwitchManagement(4).SecurityConfiguration(80).MacLimiters(11).MACLimitersPortTable(5)
--
--	swhMacLimitersPortTable OBJECT-TYPE
--		SYNTAX    SEQUENCE OF SwhMACLimitersPortEntry
--		ACCESS    not-accessible
--		STATUS    mandatory
--		DESCRIPTION
--			"Table of Port MAC Limiters."
--		::= { swhMacLimiters 5 }
--
	-- Table Entry
--	swhMacLimitersPortEntry OBJECT-TYPE
--		SYNTAX    SwhMACLimitersPortEntry
--		ACCESS    not-accessible
--		STATUS    mandatory
--		DESCRIPTION
--			"An entry in the table, containing information
--			about Port MAC Limiters."
--		INDEX    { swhMacLimitersPortIndex }
--		::= { swhMacLimitersPortTable 1 }
--
--	SwhMACLimitersPortEntry ::=
--		SEQUENCE {
--			swhMacLimitersPortIndex
--				INTEGER,
--			swhMacLimitersPortEnable
--				INTEGER,
--			swhMacLimitersPortLimit
--				INTEGER,
--			swhMacLimitersPortSticky
--				INTEGER,
--			swhMacLimitersPortAction
--				INTEGER,
--			swhMacLimitersPortUnlock
--				INTEGER
--		}
--
--	swhMacLimitersPortIndex OBJECT-TYPE
--		SYNTAX    INTEGER (0..2147483647)
--		ACCESS    not-accessible
--		STATUS    mandatory
--		DESCRIPTION
--			"A unique value for each Port."
--		::= { swhMacLimitersPortEntry 1 }
--
--	swhMacLimitersPortEnable OBJECT-TYPE
--		SYNTAX    INTEGER { disable(0), enable(1) }
--		ACCESS    read-write
--		STATUS    mandatory
--		DESCRIPTION
--			"Port is Disable or Enable"
--		::= { swhMacLimitersPortEntry 2 }
--
--	swhMacLimitersPortLimit OBJECT-TYPE
--		SYNTAX    INTEGER
--		ACCESS    read-write
--		STATUS    mandatory
--		DESCRIPTION
--			"Port Limit(1-50)"
--		::= { swhMacLimitersPortEntry 3 }
--
--	swhMacLimitersPortSticky OBJECT-TYPE
--		SYNTAX    INTEGER { disable(0), enable(1) }
--		ACCESS    read-write
--		STATUS    mandatory
--		DESCRIPTION
--			"Port Sticky is Disable or Enable"
--		::= { swhMacLimitersPortEntry 4 }
--
--    swhMacLimitersPortAction OBJECT-TYPE
--		SYNTAX    INTEGER { drop(1), shutdown(4) }
--		ACCESS    read-write
--		STATUS    mandatory
--		DESCRIPTION
--			"Port Limit Action Drop or Shutdown"
--		::= { swhMacLimitersPortEntry 5 }
--
--	swhMacLimitersPortUnlock OBJECT-TYPE
--		SYNTAX    INTEGER { unlock(1) }
--		ACCESS    read-write
--		STATUS    mandatory
--		DESCRIPTION
--			"Unlock."
--		::= { swhMacLimitersPortEntry 6 }


-- SwitchManagement(4).SecurityConfiguration(80).StormControl(12)

	swhStormControlEnable OBJECT-TYPE
		SYNTAX    INTEGER { disable(0), enable(1) }
		ACCESS    read-write
		STATUS    mandatory
		DESCRIPTION
			"Storm Control Enable/Disable"
		::= { swhStormControl 16 }

	swhThresholdInterval OBJECT-TYPE
		SYNTAX    INTEGER (0..2147483647)
		ACCESS    read-write
		STATUS    mandatory
		DESCRIPTION
			"Threshold Interval (120-86400)secs"
		::= { swhStormControl 3 }

-- SwitchManagement(4).SecurityConfiguration(80).StormControl(12).StormControlTable(9)

	swhSecurityStormControlTable OBJECT-TYPE
		SYNTAX    SEQUENCE OF SwhSecurityStormControlEntry
		ACCESS    not-accessible
		STATUS    mandatory
		DESCRIPTION
			"Table of Storm Control."
		::= { swhStormControl 9 }

	-- Table Entry
	swhSecurityStormControlEntry OBJECT-TYPE
		SYNTAX    SwhSecurityStormControlEntry
		ACCESS    not-accessible
		STATUS    mandatory
		DESCRIPTION
			"An entry in the table, containing information
			 about Port Storm Control."
		INDEX    { swhSecurityStormControlIndex }
		::= { swhSecurityStormControlTable 1 }

	SwhSecurityStormControlEntry ::=
		SEQUENCE {
			swhSecurityStormControlIndex
				INTEGER,
			swhSecurityStormControlPortConfigPort
				DisplayString,
			swhSecurityStormControlUnknownUnicastRate
				INTEGER,
			swhSecurityStormControlUnknownMulticastRate
				INTEGER,
			swhSecurityStormControlBroadcastRate
				INTEGER
		}

	swhSecurityStormControlIndex OBJECT-TYPE
		SYNTAX    INTEGER (0..2147483647)
		ACCESS    read-only
		STATUS    mandatory
		DESCRIPTION
			"A unique value for each port."
		::= { swhSecurityStormControlEntry 1 }

	swhSecurityStormControlPortConfigPort OBJECT-TYPE
		SYNTAX    DisplayString
		ACCESS    read-only
		STATUS    mandatory
		DESCRIPTION
			"Security StormControl Port Number."
		::= { swhSecurityStormControlEntry 12 }

	swhSecurityStormControlUnknownUnicastRate OBJECT-TYPE
		SYNTAX    INTEGER { none(-1),
		                    off(0),
		                    rate-1(1),
		                    rate-2(2),
		                    rate-4(3),
		                    rate-8(4),
		                    rate-16(5),
		                    rate-32(6),
		                    rate-64(7),
		                    rate-128(8),
		                    rate-256(9),
		                    rate-512(10),
		                    rate-1K(11),
		                    rate-2K(12),
		                    rate-4K(13),
		                    rate-8K(14),
		                    rate-16K(15),
		                    rate-32K(16),
		                    rate-64K(17),
		                    rate-128K(18),
		                    rate-256K(19)
		                    }
		ACCESS    read-write
		STATUS    mandatory
		DESCRIPTION
			"Unknown Unicast Rate (packets/second)"
		::= { swhSecurityStormControlEntry 11 }

	swhSecurityStormControlUnknownMulticastRate OBJECT-TYPE
		SYNTAX    INTEGER { none(-1),
		                    off(0),
		                    rate-1(1),
		                    rate-2(2),
		                    rate-4(3),
		                    rate-8(4),
		                    rate-16(5),
		                    rate-32(6),
		                    rate-64(7),
		                    rate-128(8),
		                    rate-256(9),
		                    rate-512(10),
		                    rate-1K(11),
		                    rate-2K(12),
		                    rate-4K(13),
		                    rate-8K(14),
		                    rate-16K(15),
		                    rate-32K(16),
		                    rate-64K(17),
		                    rate-128K(18),
		                    rate-256K(19)
		                    }
		ACCESS    read-write
		STATUS    mandatory
		DESCRIPTION
			"Unknown Multicast Rate (packets/second)"
		::= { swhSecurityStormControlEntry 10 }

	swhSecurityStormControlBroadcastRate OBJECT-TYPE
		SYNTAX    INTEGER { none(-1),
		                    off(0),
		                    rate-1(1),
		                    rate-2(2),
		                    rate-4(3),
		                    rate-8(4),
		                    rate-16(5),
		                    rate-32(6),
		                    rate-64(7),
		                    rate-128(8),
		                    rate-256(9),
		                    rate-512(10),
		                    rate-1K(11),
		                    rate-2K(12),
		                    rate-4K(13),
		                    rate-8K(14),
		                    rate-16K(15),
		                    rate-32K(16),
		                    rate-64K(17),
		                    rate-128K(18),
		                    rate-256K(19)
		                    }
		ACCESS    read-write
		STATUS    mandatory
		DESCRIPTION
			"Broadcast Rate (packets/second)"
		::= { swhSecurityStormControlEntry 8 }


-- SwitchManagement(4).SecurityConfiguration(80).PortIsolationConfiguration(13)

	swhPortIsolationConfigPortIsolation OBJECT-TYPE
		SYNTAX    INTEGER { disable(0), enable(1) }
		ACCESS    read-write
		STATUS    mandatory
		DESCRIPTION
			"Port Isolation is disable or enable.
			 When you enable Port Isolation, Port Based VLAN is automatically invalid."
		::= { swhPortIsolationConfiguration 1 }

	swhPortIsolationConfigUplinkPortList OBJECT-TYPE
		SYNTAX    DisplayString (SIZE (0..255))
		ACCESS    read-write
		STATUS    mandatory
		DESCRIPTION
			"Uplink Port List."
		::= { swhPortIsolationConfiguration 2 }


-- SwitchManagement(4).SecurityConfiguration(80).PortLinkupDelay(15)

	swhLinkupDelayTime OBJECT-TYPE
		SYNTAX    INTEGER (0..1200)
		ACCESS    read-write
		STATUS    mandatory
		DESCRIPTION
			"Delay Time(0-1200 Secs)"
		::= { swhPortLinkupDelay 1 }

	swhLinkupDelayPortList OBJECT-TYPE
		SYNTAX    DisplayString
		ACCESS    read-write
		STATUS    mandatory
		DESCRIPTION
			"Delay Port List.(e.g: 1,2,5-7)"
		::= { swhPortLinkupDelay 2 }

--	swhLinkupReleaseDelayRule OBJECT-TYPE
--		SYNTAX    INTEGER { followdelaytime(0), mac-limit(1) }
--		ACCESS    read-write
--		STATUS    mandatory
--		DESCRIPTION
--			"Release Delay Rule"
--		::= { swhPortLinkupDelay 3 }

--	swhLinkupReleaseDelayTriggerPortList OBJECT-TYPE
--		SYNTAX    DisplayString
--		ACCESS    read-write
--		STATUS    mandatory
--		DESCRIPTION
--			"Release Delay Trigger Port List.(e.g: 1,2,5-7)"
--		::= { swhPortLinkupDelay 4 }


-- SwitchManagement(4).SecurityConfiguration(80).PortLinkFlap(16)

	swhPortLinkFlapThreshold OBJECT-TYPE
		SYNTAX    INTEGER (1..20)
		ACCESS    read-write
		STATUS    mandatory
		DESCRIPTION
			"Threshold(1-20 Times)"
		::= { swhPortLinkFlap 1 }


-- SwitchManagement(4).FilterConfiguration(83)


-- SwitchManagement(4).FilterConfiguration(83).DHCPServerTrustPort(7)


-- SwitchManagement(4).FilterConfiguration(83).DHCPServerTrustPort(7).DHCPServerTable(1)


-- SwitchManagement(4).HTTPAuthentication(90)


-- SwitchManagement(4).FastRedundancy(91)


-- SwitchManagement(4).IGMPMVR(92)
--
--
--	swhIGMPMVRSystem
--		OBJECT IDENTIFIER ::= { swhIGMPMVR 1 }
--	swhIGMPMVRPort
--		OBJECT IDENTIFIER ::= { swhIGMPMVR 2 }
--	swhIGMPMVRMulticast
--		OBJECT IDENTIFIER ::= { swhIGMPMVR 3 }
--
--
-- SwitchManagement(4).IGMPMVR(92).IGMPMVRSystem(1)
--
--
--	swhIGMPMVRSystemEnable OBJECT-TYPE
--		SYNTAX    INTEGER { disable(0), enable(1) }
--		ACCESS    read-write
--		STATUS    mandatory
--		DESCRIPTION
--			"IGMP MVR is Disable or Enable"
--		::= { swhIGMPMVRSystem 1 }
--
--	swhIGMPMVRSystemSortBy OBJECT-TYPE
--		SYNTAX    INTEGER { index(0), mvr(1) }
--		ACCESS    read-write
--		STATUS    mandatory
--		DESCRIPTION
--			"IGMP MVR Group SortBy"
--		::= { swhIGMPMVRSystem 2 }
--
--
-- SwitchManagement(4).IGMPMVR(92).IGMPMVRSystem(1).IGMPMVRSystemConfigTable(5)
--
--
--	swhIGMPMVRSystemConfigTable OBJECT-TYPE
--		SYNTAX    SEQUENCE OF SwhIGMPMVRSystemConfigEntry
--		ACCESS    not-accessible
--		STATUS    mandatory
--		DESCRIPTION
--			"Table of IGMP MVR Group."
--		::= { swhIGMPMVRSystem 5 }
--
	-- Table Entry
--	swhIGMPMVRSystemConfigEntry OBJECT-TYPE
--		SYNTAX    SwhIGMPMVRSystemConfigEntry
--		ACCESS    not-accessible
--		STATUS    mandatory
--		DESCRIPTION
--			"An entry in the table, containing information
--			about Layer 2 Protocol Tunneling Configuration"
--		INDEX    { swhIGMPMVRSystemConfigConfig }
--		::= { swhIGMPMVRSystemConfigTable 1 }
--
--	SwhIGMPMVRSystemConfigEntry ::=
--		SEQUENCE {
--			swhIGMPMVRSystemConfigConfig
--				INTEGER,
--			swhIGMPMVRSystemConfigIndex
--				INTEGER,
--			swhIGMPMVRSystemConfigMVRVLAN
--				INTEGER,
--			swhIGMPMVRSystemConfigName
--				DisplayString,
--			swhIGMPMVRSystemConfigEnable
--				INTEGER,
--			swhIGMPMVRSystemConfigPriority
--				INTEGER,
--			swhIGMPMVRSystemConfigDelete
--				INTEGER
--		}
--
--	swhIGMPMVRSystemConfigConfig OBJECT-TYPE
--		SYNTAX    INTEGER (0..2147483647)
--		ACCESS    read-only
--		STATUS    mandatory
--		DESCRIPTION
--			"A unique value for IGMP MVR index."
--		::= { swhIGMPMVRSystemConfigEntry 1 }
--
--	swhIGMPMVRSystemConfigIndex OBJECT-TYPE
--		SYNTAX    INTEGER (0..2147483647)
--		ACCESS    read-only
--		STATUS    mandatory
--		DESCRIPTION
--			"A unique value for IGMP MVR index."
--		::= { swhIGMPMVRSystemConfigEntry 2 }
--
--	swhIGMPMVRSystemConfigMVRVLAN OBJECT-TYPE
--		SYNTAX    INTEGER (0..2147483647)
--		ACCESS    read-write
--		STATUS    mandatory
--		DESCRIPTION
--			"MVR VLAN."
--		::= { swhIGMPMVRSystemConfigEntry 3 }
--
--	swhIGMPMVRSystemConfigName OBJECT-TYPE
--		SYNTAX    DisplayString
--		ACCESS    read-write
--		STATUS    mandatory
--		DESCRIPTION
--			"MVR Name."
--		::= { swhIGMPMVRSystemConfigEntry 4 }
--
--	swhIGMPMVRSystemConfigEnable OBJECT-TYPE
--		SYNTAX    INTEGER { disable(0), enable(1) }
--		ACCESS    read-write
--		STATUS    mandatory
--		DESCRIPTION
--			"MVR Enable."
--		::= { swhIGMPMVRSystemConfigEntry 5 }
--
--	swhIGMPMVRSystemConfigPriority OBJECT-TYPE
--		SYNTAX    INTEGER (0..7)
--		ACCESS    read-write
--		STATUS    mandatory
--		DESCRIPTION
--			"Specify Priority(0-7)."
--		::= { swhIGMPMVRSystemConfigEntry 6 }
--
--	swhIGMPMVRSystemConfigDelete OBJECT-TYPE
--		SYNTAX    INTEGER { normal(0), delete(1) }
--		ACCESS    read-write
--		STATUS    mandatory
--		DESCRIPTION
--			"Delete this entry."
--		::= { swhIGMPMVRSystemConfigEntry 7 }
--
--
-- SwitchManagement(4).IGMPMVR(92).IGMPMVRPort(2)
--
--
--	swhIGMPMVRPortSortBy OBJECT-TYPE
--		SYNTAX    INTEGER { index(0), mvr(1), port(2) }
--		ACCESS    read-write
--		STATUS    mandatory
--		DESCRIPTION
--			"IGMP MVR Port SortBy"
--		::= { swhIGMPMVRPort 2 }
--
--
-- SwitchManagement(4).IGMPMVR(92).IGMPMVRPort(2).IGMPMVRPortConfigTable(5)
--
--
--	swhIGMPMVRPortConfigTable OBJECT-TYPE
--		SYNTAX    SEQUENCE OF SwhIGMPMVRPortConfigEntry
--		ACCESS    not-accessible
--		STATUS    mandatory
--		DESCRIPTION
--			"Table of IGMP MVR Port."
--		::= { swhIGMPMVRPort 5 }
--
	-- Table Entry
--	swhIGMPMVRPortConfigEntry OBJECT-TYPE
--		SYNTAX    SwhIGMPMVRPortConfigEntry
--		ACCESS    not-accessible
--		STATUS    mandatory
--		DESCRIPTION
--			"An entry in the table, containing information
--			about Layer 2 Protocol Tunneling Configuration"
--		INDEX    { swhIGMPMVRPortConfigConfig }
--		::= { swhIGMPMVRPortConfigTable 1 }
--
--	SwhIGMPMVRPortConfigEntry ::=
--		SEQUENCE {
--			swhIGMPMVRPortConfigConfig
--				INTEGER,
--			swhIGMPMVRPortConfigIndex
--				INTEGER,
--			swhIGMPMVRPortConfigMVRVLAN
--				INTEGER,
--			swhIGMPMVRPortConfigPort
--				INTEGER,
--			swhIGMPMVRPortConfigPortType
--				INTEGER,
--			swhIGMPMVRPortConfigRecVLAN
--				DisplayString
--			swhIGMPMVRPortConfigDelete
--				INTEGER
--		}
--
--	swhIGMPMVRPortConfigConfig OBJECT-TYPE
--		SYNTAX    INTEGER (0..2147483647)
--		ACCESS    read-only
--		STATUS    mandatory
--		DESCRIPTION
--			"A unique value for IGMP MVR Port config."
--		::= { swhIGMPMVRPortConfigEntry 1 }
--
--	swhIGMPMVRPortConfigIndex OBJECT-TYPE
--		SYNTAX    INTEGER (0..2147483647)
--		ACCESS    read-only
--		STATUS    mandatory
--		DESCRIPTION
--			"A unique value for IGMP MVR Port index."
--		::= { swhIGMPMVRPortConfigEntry 2 }
--
--	swhIGMPMVRPortConfigMVRVLAN OBJECT-TYPE
--		SYNTAX    INTEGER (0..2147483647)
--		ACCESS    read-write
--		STATUS    mandatory
--		DESCRIPTION
--			"MVR VLAN."
--		::= { swhIGMPMVRPortConfigEntry 3 }
--
--	swhIGMPMVRPortConfigPort OBJECT-TYPE
--		SYNTAX    INTEGER { port01(0),
--		                    port02(1),
--		                    port03(2),
--		                    port04(3),
--		                    port05(4),
--		                    port06(5)
--		                    }
--		ACCESS    read-write
--		STATUS    mandatory
--		DESCRIPTION
--			"MVR Port."
--		::= { swhIGMPMVRPortConfigEntry 4 }
--
--	swhIGMPMVRPortConfigPortType OBJECT-TYPE
--		SYNTAX    INTEGER { receiver(0), sender(1) }
--		ACCESS    read-write
--		STATUS    mandatory
--		DESCRIPTION
--			"MVR Port Type."
--		::= { swhIGMPMVRPortConfigEntry 5 }
--
--	swhIGMPMVRPortConfigRecVLAN OBJECT-TYPE
--		SYNTAX    DisplayString
--		ACCESS    read-write
--		STATUS    mandatory
--		DESCRIPTION
--			"MVR Port."
--		::= { swhIGMPMVRPortConfigEntry 6 }
--
--	swhIGMPMVRPortConfigDelete OBJECT-TYPE
--		SYNTAX    INTEGER { normal(0), delete(1) }
--		ACCESS    read-write
--		STATUS    mandatory
--		DESCRIPTION
--			"Delete this entry."
--		::= { swhIGMPMVRPortConfigEntry 7 }
--
--
-- SwitchManagement(4).IGMPMVR(92).IGMPMVRMulticast(3)
--
--
--	swhIGMPMVRMulticastSortBy OBJECT-TYPE
--		SYNTAX    INTEGER { index(0), mvr(1), multicast(2) }
--		ACCESS    read-write
--		STATUS    mandatory
--		DESCRIPTION
--			"IGMP MVR Port SortBy"
--		::= { swhIGMPMVRMulticast 2 }
--
--
-- SwitchManagement(4).IGMPMVR(92).IGMPMVRMulticast(3).IGMPMVRMulticastConfigTable(5)
--
--
--	swhIGMPMVRMulticastConfigTable OBJECT-TYPE
--		SYNTAX    SEQUENCE OF SwhIGMPMVRMulticastConfigEntry
--		ACCESS    not-accessible
--		STATUS    mandatory
--		DESCRIPTION
--			"Table of IGMP MVR Multicast."
--		::= { swhIGMPMVRMulticast 5 }
--
	-- Table Entry
--	swhIGMPMVRMulticastConfigEntry OBJECT-TYPE
--		SYNTAX    SwhIGMPMVRMulticastConfigEntry
--		ACCESS    not-accessible
--		STATUS    mandatory
--		DESCRIPTION
--			"An entry in the table, containing information
--			about Layer 2 Protocol Tunneling Configuration"
--		INDEX    { swhIGMPMVRMulticastConfigConfig }
--		::= { swhIGMPMVRMulticastConfigTable 1 }
--
--	SwhIGMPMVRMulticastConfigEntry ::=
--		SEQUENCE {
--			swhIGMPMVRMulticastConfigConfig
--				INTEGER,
--			swhIGMPMVRMulticastConfigIndex
--				INTEGER,
--			swhIGMPMVRMulticastConfigMVRVLAN
--				INTEGER,
--			swhIGMPMVRMulticastConfigIPType
--				INTEGER,
--			swhIGMPMVRMulticastConfigIPRange1
--				DisplayString,
--			swhIGMPMVRMulticastConfigIPRange2
--				DisplayString,
--			swhIGMPMVRMulticastConfigDelete
--				INTEGER
--		}
--
--	swhIGMPMVRMulticastConfigConfig OBJECT-TYPE
--		SYNTAX    INTEGER (0..2147483647)
--		ACCESS    read-only
--		STATUS    mandatory
--		DESCRIPTION
--			"A unique value for IGMP MVR Port index."
--		::= { swhIGMPMVRMulticastConfigEntry 1 }
--
--	swhIGMPMVRMulticastConfigIndex OBJECT-TYPE
--		SYNTAX    INTEGER (0..2147483647)
--		ACCESS    read-only
--		STATUS    mandatory
--		DESCRIPTION
--			"A unique value for IGMP MVR Port index."
--		::= { swhIGMPMVRMulticastConfigEntry 2 }
--
--	swhIGMPMVRMulticastConfigMVRVLAN OBJECT-TYPE
--		SYNTAX    INTEGER (0..2147483647)
--		ACCESS    read-write
--		STATUS    mandatory
--		DESCRIPTION
--			"MVR VLAN."
--		::= { swhIGMPMVRMulticastConfigEntry 3 }
--
--	swhIGMPMVRMulticastConfigIPType OBJECT-TYPE
--		SYNTAX    INTEGER { IPv4(0), IPv6(1) }
--		ACCESS    read-write
--		STATUS    mandatory
--		DESCRIPTION
--			"MVR Port."
--		::= { swhIGMPMVRMulticastConfigEntry 4 }
--
--	swhIGMPMVRMulticastConfigIPRange1 OBJECT-TYPE
--		SYNTAX    DisplayString
--		ACCESS    read-write
--		STATUS    mandatory
--		DESCRIPTION
--			"IP Range1 Address"
--		::= { swhIGMPMVRMulticastConfigEntry 5 }
--
--	swhIGMPMVRMulticastConfigIPRange2 OBJECT-TYPE
--		SYNTAX    DisplayString
--		ACCESS    read-write
--		STATUS    mandatory
--		DESCRIPTION
--			"IP Range2 Address"
--		::= { swhIGMPMVRMulticastConfigEntry 6 }
--
--	swhIGMPMVRMulticastConfigDelete OBJECT-TYPE
--		SYNTAX    INTEGER { normal(0), delete(1) }
--		ACCESS    read-write
--		STATUS    mandatory
--		DESCRIPTION
--			"Delete this entry."
--		::= { swhIGMPMVRMulticastConfigEntry 7 }

-- SwitchManagement(4).LANFollowWAN(80)

	swhLANFollowWANEnable OBJECT-TYPE
		SYNTAX    INTEGER { disable(0), enable(1) }
		ACCESS    read-write
		STATUS    mandatory
		DESCRIPTION
			"LAN Follow WAN is disable or enable."
		::= { swhLANFollowWAN 1 }

	swhLANFollowWANPort OBJECT-TYPE
		SYNTAX    DisplayString (SIZE (0..255))
		ACCESS    read-write
		STATUS    mandatory
		DESCRIPTION
			"Uplink Port List."
		::= { swhLANFollowWAN 2 }

	swhLANFollowWANDownTimer OBJECT-TYPE
		SYNTAX    INTEGER
		ACCESS    read-write
		STATUS    mandatory
		DESCRIPTION
			"LAN Follow WAN, WAN Down Timer."
		::= { swhLANFollowWAN 3 }

	swhLANFollowWANUpTimer OBJECT-TYPE
		SYNTAX    INTEGER
		ACCESS    read-write
		STATUS    mandatory
		DESCRIPTION
			"LAN Follow WAN, WAN Up Timer."
		::= { swhLANFollowWAN 4 }


-- SwitchMonitor(5)

	swhCPUAndMemoryStatistics
		OBJECT IDENTIFIER ::= { swhSwitchMonitor 45 }
	swhPortStatus
		OBJECT IDENTIFIER ::= { swhSwitchMonitor 1 }
	swh8021QTagVLAN
		OBJECT IDENTIFIER ::= { swhSwitchMonitor 3 }
	swhPortCountersRates
		OBJECT IDENTIFIER ::= { swhSwitchMonitor 5 }
	swhPortCountersEvents
		OBJECT IDENTIFIER ::= { swhSwitchMonitor 6 }
--	swhLACPPortStatus
--		OBJECT IDENTIFIER ::= { swhSwitchMonitor 22 }
--	swhLACPStatistics
--		OBJECT IDENTIFIER ::= { swhSwitchMonitor 24 }
--	swhSTPStatus
--		OBJECT IDENTIFIER ::= { swhSwitchMonitor 56 }
	--swhRSTPBridgeOverview
		--OBJECT IDENTIFIER ::= { swhSwitchMonitor 10 }
	--swhRSTPPortStatus
		--OBJECT IDENTIFIER ::= { swhSwitchMonitor 14 }
	--swhRSTPStatistics
		--OBJECT IDENTIFIER ::= { swhSwitchMonitor 18 }
	swh8021XPortStatus
		OBJECT IDENTIFIER ::= { swhSwitchMonitor 32 }
	swh8021XStatistics
		OBJECT IDENTIFIER ::= { swhSwitchMonitor 33 }
	swhIGMPStatus
		OBJECT IDENTIFIER ::= { swhSwitchMonitor 26 }
	swhMLDStatus
		OBJECT IDENTIFIER ::= { swhSwitchMonitor 27 }
	swhIGMPGroupTable
		OBJECT IDENTIFIER ::= { swhSwitchMonitor 28 }
	swhSFPInformation
		OBJECT IDENTIFIER ::= { swhSwitchMonitor 34 }
	swhDHCPSnoopingTable
		OBJECT IDENTIFIER ::= { swhSwitchMonitor 35 }
	swhMLDGroupTable
		OBJECT IDENTIFIER ::= { swhSwitchMonitor 29 }
--	swhMacLimitersStatus
--		OBJECT IDENTIFIER ::= { swhSwitchMonitor 39 }
	swhMacAddressTable
		OBJECT IDENTIFIER ::= { swhSwitchMonitor 7 }
--	swhLayer2ProtocolTunnelStatus
--		OBJECT IDENTIFIER ::= { swhSwitchMonitor 25 }
--	swhLLDPStatus
--		OBJECT IDENTIFIER ::= { swhSwitchMonitor 11 }
	swhLoopDetectionStatus
		OBJECT IDENTIFIER ::= { swhSwitchMonitor 36 }
--	swhDIStatus
--		OBJECT IDENTIFIER ::= { swhSwitchMonitor 41 }
	swhCPUTemperatureStatus
		OBJECT IDENTIFIER ::= { swhSwitchMonitor 51 }
--	swhFanSpeedState
--		OBJECT IDENTIFIER ::= { swhSwitchMonitor 54 }
--	swhSystemVoltageState
--		OBJECT IDENTIFIER ::= { swhSwitchMonitor 55 }


-- SwitchMonitor(5).PortState(1)

	swhPortStatusTable OBJECT-TYPE
		SYNTAX    SEQUENCE OF SwhPortStatusEntry
		ACCESS    not-accessible
		STATUS    mandatory
		DESCRIPTION
			"Table of Port State."
		::= { swhPortStatus 1 }

	-- Table Entry
	swhPortStatusEntry OBJECT-TYPE
		SYNTAX    SwhPortStatusEntry
		ACCESS    not-accessible
		STATUS    mandatory
		DESCRIPTION
			"An entry in the table, containing information
			 about Port State."
		INDEX    { swhPortStatusIndex }
		::= { swhPortStatusTable 1 }

	SwhPortStatusEntry ::=
		SEQUENCE {
			swhPortStatusIndex
				INTEGER,
			swhPortStatusPortMedia
				INTEGER,
			swhPortStatusPortState
				INTEGER,
			swhPortStatusPortReason
				INTEGER,
			swhPortStatusPortLink
				INTEGER,
			swhPortStatusPortSpeed
				INTEGER,
			swhPortStatusPortDuplex
				INTEGER,
			swhPortStatusPortFlowCtrl
				INTEGER,
			swhPortStatusDescription
				DisplayString
		}

	swhPortStatusIndex OBJECT-TYPE
		SYNTAX    INTEGER (0..2147483647)
		ACCESS    not-accessible
		STATUS    mandatory
		DESCRIPTION
			"A unique value for each port."
		::= { swhPortStatusEntry 1 }

	swhPortStatusDescription OBJECT-TYPE
		SYNTAX    DisplayString
		ACCESS    read-only
		STATUS    mandatory
		DESCRIPTION
			"Port Description"
		::= { swhPortStatusEntry 2 }

	swhPortStatusPortMedia OBJECT-TYPE
		SYNTAX    INTEGER { na2(-2), na(-1), tx(1), fx(2) }
		ACCESS    read-only
		STATUS    mandatory
		DESCRIPTION
			"Port Media Type"
		::= { swhPortStatusEntry 3 }

	swhPortStatusPortState OBJECT-TYPE
		SYNTAX    INTEGER { na2(-2), na(-1), disable(0), blocking-listening(1), learning(2), forwarding(3) }
		ACCESS    read-only
		STATUS    mandatory
		DESCRIPTION
			"Port State"
		::= { swhPortStatusEntry 4 }

	swhPortStatusPortReason OBJECT-TYPE
		SYNTAX    INTEGER { na2(-2), na(-1), link-down(0), loop(1), mac-limit(2), storm(3) }
		ACCESS    read-only
		STATUS    mandatory
		DESCRIPTION
			"Port State Reason"
		::= { swhPortStatusEntry 14 }

	swhPortStatusPortLink OBJECT-TYPE
		SYNTAX    INTEGER { na2(-2), na(-1), up(1), down(2) }
		ACCESS    read-only
		STATUS    mandatory
		DESCRIPTION
			"Port Link"
		::= { swhPortStatusEntry 5 }

	swhPortStatusPortSpeed OBJECT-TYPE
		SYNTAX    INTEGER { na2(-2), na(-1) }
		ACCESS    read-only
		STATUS    mandatory
		DESCRIPTION
			"Port Speed"
		::= { swhPortStatusEntry 6 }

	swhPortStatusPortDuplex OBJECT-TYPE
		SYNTAX    INTEGER { na2(-2), na(-1), full(1), half(2) }
		ACCESS    read-only
		STATUS    mandatory
		DESCRIPTION
			"Port Duplex"
		::= { swhPortStatusEntry 7 }

	swhPortStatusPortFlowCtrl OBJECT-TYPE
		SYNTAX    INTEGER { na2(-2), na(-1), on(1), off(2) }
		ACCESS    read-only
		STATUS    mandatory
		DESCRIPTION
			"Port Flow Control"
		::= { swhPortStatusEntry 8 }


-- SwitchMonitor(5).8021QTagVLAN(3)

	swh8021QTagVLANTable OBJECT-TYPE
		SYNTAX    SEQUENCE OF Swh8021QTagVLANEntry
		ACCESS    not-accessible
		STATUS    mandatory
		DESCRIPTION
			"Table of 802.1Q Tag VLAN Configuration."
		::= { swh8021QTagVLAN 1 }

	-- Table Entry
	swh8021QTagVLANEntry OBJECT-TYPE
		SYNTAX    Swh8021QTagVLANEntry
		ACCESS    not-accessible
		STATUS    mandatory
		DESCRIPTION
			"An entry in the table, containing information
			about tag vlan config."
		INDEX    { swh8021QTagVLANIndex }
		::= { swh8021QTagVLANTable 1 }

	Swh8021QTagVLANEntry ::=
		SEQUENCE {
			swh8021QTagVLANIndex
				INTEGER,
--			swh8021QTagVLANValid
--				INTEGER,
			swh8021QTagVLANVID
				INTEGER,
--			swh8021QTagVLANIsMVRVID
--				INTEGER,
			swh8021QTagVLANName
				DisplayString,
			swh8021QTagVLANPort1
				INTEGER,
			swh8021QTagVLANPort2
				INTEGER,
			swh8021QTagVLANPort3
				INTEGER,
			swh8021QTagVLANPort4
				INTEGER,
			swh8021QTagVLANPort5
				INTEGER,
			swh8021QTagVLANPort6
				INTEGER,
			swh8021QTagVLANCPU
				INTEGER
		}

	swh8021QTagVLANIndex OBJECT-TYPE
		SYNTAX    INTEGER (0..2147483647)
		ACCESS    not-accessible
		STATUS    mandatory
		DESCRIPTION
			"A unique value for each vlan."
		::= { swh8021QTagVLANEntry 1 }

--	swh8021QTagVLANValid OBJECT-TYPE
--		SYNTAX    INTEGER { invalid(0), valid(1) }
--		ACCESS    read-only
--		STATUS    mandatory
--		DESCRIPTION
--			"This vlan setting is valid or invalid."
--		::= { swh8021QTagVLANEntry 2 }

	swh8021QTagVLANVID OBJECT-TYPE
		SYNTAX    INTEGER (1..4094)
		ACCESS    read-only
		STATUS    mandatory
		DESCRIPTION
			"VLAN ID"
		::= { swh8021QTagVLANEntry 3 }

	swh8021QTagVLANName OBJECT-TYPE
		SYNTAX    DisplayString
		ACCESS    read-only
		STATUS    mandatory
		DESCRIPTION
			"Port based vlan name."
		::= { swh8021QTagVLANEntry 4 }

	swh8021QTagVLANPort1 OBJECT-TYPE
		SYNTAX    INTEGER { b(0), t(2), u(3), d(4), s(5), r(6), q(7) }
		ACCESS    read-only
		STATUS    mandatory
		DESCRIPTION
			"b:Blocked  t:Tagged u:Untagged d:Dot1q-Tunnel s:MVR-sender r:MVR-receiver q:Selective-QinQ"
		::= { swh8021QTagVLANEntry 5 }

	swh8021QTagVLANPort2 OBJECT-TYPE
		SYNTAX    INTEGER { b(0), t(2), u(3), d(4), s(5), r(6), q(7) }
		ACCESS    read-only
		STATUS    mandatory
		DESCRIPTION
			"b:Blocked  t:Tagged u:Untagged d:Dot1q-Tunnel s:MVR-sender r:MVR-receiver q:Selective-QinQ"
		::= { swh8021QTagVLANEntry 6 }

	swh8021QTagVLANPort3 OBJECT-TYPE
		SYNTAX    INTEGER { b(0), t(2), u(3), d(4), s(5), r(6), q(7) }
		ACCESS    read-only
		STATUS    mandatory
		DESCRIPTION
			"b:Blocked  t:Tagged u:Untagged d:Dot1q-Tunnel s:MVR-sender r:MVR-receiver q:Selective-QinQ"
		::= { swh8021QTagVLANEntry 7 }

	swh8021QTagVLANPort4 OBJECT-TYPE
		SYNTAX    INTEGER { b(0), t(2), u(3), d(4), s(5), r(6), q(7) }
		ACCESS    read-only
		STATUS    mandatory
		DESCRIPTION
			"b:Blocked  t:Tagged u:Untagged d:Dot1q-Tunnel s:MVR-sender r:MVR-receiver q:Selective-QinQ"
		::= { swh8021QTagVLANEntry 8 }

	swh8021QTagVLANPort5 OBJECT-TYPE
		SYNTAX    INTEGER { b(0), t(2), u(3), d(4), s(5), r(6), q(7) }
		ACCESS    read-only
		STATUS    mandatory
		DESCRIPTION
			"b:Blocked  t:Tagged u:Untagged d:Dot1q-Tunnel s:MVR-sender r:MVR-receiver q:Selective-QinQ"
		::= { swh8021QTagVLANEntry 9 }

	swh8021QTagVLANPort6 OBJECT-TYPE
		SYNTAX    INTEGER { b(0), t(2), u(3), d(4), s(5), r(6), q(7) }
		ACCESS    read-only
		STATUS    mandatory
		DESCRIPTION
			"b:Blocked  t:Tagged u:Untagged d:Dot1q-Tunnel s:MVR-sender r:MVR-receiver q:Selective-QinQ"
		::= { swh8021QTagVLANEntry 10 }


--	swh8021QTagVLANIsMVRVID OBJECT-TYPE
--		SYNTAX    INTEGER { b(0), v(1) }
--		ACCESS    read-only
--		STATUS    mandatory
--		DESCRIPTION
--			"Is it MVR VLAN ID? v: yes, b: no"
--		::= { swh8021QTagVLANEntry 53 }

	swh8021QTagVLANCPU OBJECT-TYPE
		SYNTAX    INTEGER { b(0), v(1) }
		ACCESS    read-only
		STATUS    mandatory
		DESCRIPTION
			"b:Blocked  v:Member"
		::= { swh8021QTagVLANEntry 55 }


-- SwitchMonitor(5).PortInformation(4)


-- SwitchMonitor(5).PortCountersRates(5)

	swhCountersRatesTable OBJECT-TYPE
		SYNTAX    SEQUENCE OF SwhCountersRatesEntry
		ACCESS    not-accessible
		STATUS    mandatory
		DESCRIPTION
			"Table of Port counters rates."
		::= { swhPortCountersRates 1 }

	-- Table Entry
	swhCountersRatesEntry OBJECT-TYPE
		SYNTAX    SwhCountersRatesEntry
		ACCESS    not-accessible
		STATUS    mandatory
		DESCRIPTION
			"An entry in the table, containing information
			about Port counters rates mode."
		INDEX    { swhCountersRatesIndex }
		::= { swhCountersRatesTable 1 }

	SwhCountersRatesEntry ::=
		SEQUENCE {
			swhCountersRatesIndex
				INTEGER,
			swhCountersRatesBytesReceived
				Counter,
			swhCountersRatesFramesReceived
				Counter,
			swhCountersRatesReceivedUtilization
				DisplayString,
			swhCountersRatesBytesSent
				Counter,
			swhCountersRatesFramesSent
				Counter,
			swhCountersRatesSentUtilization
				DisplayString,
			swhCountersRatesTotalBytes
				Counter,
			swhCountersRatesTotalUtilization
				DisplayString,
		--	swhCountersRatesRxCRCAlignError
		--		Counter,
			swhCountersRatesRxCRCError
				Counter,
			swhCountersRatesRxAlignError
				Counter,
			swhCountersRatesRxUndersizeFrames
				Counter,
			swhCountersRatesRxFragments
				Counter,
			swhCountersRatesRxJabbers
				Counter,
			swhCountersRatesRxOversizeFrames
				Counter,
			swhCountersRatesRxDroppedFrames
				Counter,
			swhCountersRatesTxCollision
				Counter,
			swhCountersRatesTxDroppedFrames
				Counter,
			swhCountersRatesTotalErrors
				Counter,
			swhCountersRatesTotalErrorsExcludeDrop
				Counter,
			swhCountersRatesRxFrames64
				Counter,
			swhCountersRatesRxFrames65to127
				Counter,
			swhCountersRatesRxFrames128to255
				Counter,
			swhCountersRatesRxFrames256to511
				Counter,
			swhCountersRatesRxFrames512to1023
				Counter,
			swhCountersRatesRxFrames1024to1518
				Counter,
			swhCountersRatesRxFrames1519toMaxSize
				Counter,
			swhCountersRatesTxUnicastFrames
				Counter,
			swhCountersRatesTxMulticastFrames
				Counter,
			swhCountersRatesTxBroadcastFrames
				Counter,
			swhCountersRatesRxUnicastFrames
				Counter,
			swhCountersRatesRxMulticastFrames
				Counter,
			swhCountersRatesRxBroadcastFrames
				Counter
		--	swhCountersRatesRxFilteredFrames
		--		Counter,
		--	swhCountersRatesTxLateCollision
		--		Counter,
		--	swhCountersRatesTxDeferred
		--		Counter,
		--	swhCountersRatesTxTotalCollision
		--		Counter,
		--	swhCountersRatesRxFrames1024toMaxSize
		--		Counter,
		--	swhCountersRatesRxUnicastFrames
		--		Counter,
		--	swhCountersRatesTxUnicastFrames
		--		Counter,
		--	swhCountersRatesRxTotalErrors
		--		Counter,
		--	swhCountersRatesTxTotalErrors
		--		Counter,
		--	swhCountersRatesTxTotalCollisions
		--		Counter
		}

	swhCountersRatesIndex OBJECT-TYPE
		SYNTAX    INTEGER (0..2147483647)
		ACCESS    not-accessible
		STATUS    mandatory
		DESCRIPTION
			"A unique value for each Port."
		::= { swhCountersRatesEntry 1 }

	swhCountersRatesBytesReceived OBJECT-TYPE
		SYNTAX    Counter
		ACCESS    read-only
		STATUS    mandatory
		DESCRIPTION
			""
		::= { swhCountersRatesEntry 2 }

	swhCountersRatesFramesReceived OBJECT-TYPE
		SYNTAX    Counter
		ACCESS    read-only
		STATUS    mandatory
		DESCRIPTION
			""
		::= { swhCountersRatesEntry 3 }

	swhCountersRatesReceivedUtilization OBJECT-TYPE
		SYNTAX    DisplayString
		ACCESS    read-only
		STATUS    mandatory
		DESCRIPTION
			""
		::= { swhCountersRatesEntry 4 }

	swhCountersRatesBytesSent OBJECT-TYPE
		SYNTAX    Counter
		ACCESS    read-only
		STATUS    mandatory
		DESCRIPTION
			""
		::= { swhCountersRatesEntry 5 }

	swhCountersRatesFramesSent OBJECT-TYPE
		SYNTAX    Counter
		ACCESS    read-only
		STATUS    mandatory
		DESCRIPTION
			""
		::= { swhCountersRatesEntry 6 }

	swhCountersRatesSentUtilization OBJECT-TYPE
		SYNTAX    DisplayString
		ACCESS    read-only
		STATUS    mandatory
		DESCRIPTION
			""
		::= { swhCountersRatesEntry 7 }

	swhCountersRatesTotalBytes OBJECT-TYPE
		SYNTAX    Counter
		ACCESS    read-only
		STATUS    mandatory
		DESCRIPTION
			""
		::= { swhCountersRatesEntry 8 }

	swhCountersRatesTotalUtilization OBJECT-TYPE
		SYNTAX    DisplayString
		ACCESS    read-only
		STATUS    mandatory
		DESCRIPTION
			""
		::= { swhCountersRatesEntry 9 }

	swhCountersRatesRxCRCError OBJECT-TYPE
		SYNTAX    Counter
		ACCESS    read-only
		STATUS    mandatory
		DESCRIPTION
			"Units = pps"
		::= { swhCountersRatesEntry 10 }

	swhCountersRatesRxFragments OBJECT-TYPE
		SYNTAX    Counter
		ACCESS    read-only
		STATUS    mandatory
		DESCRIPTION
			"Units = pps"
		::= { swhCountersRatesEntry 11 }

--	swhCountersRatesRxFilteredFrames OBJECT-TYPE
--		SYNTAX    Counter
--		ACCESS    read-only
--		STATUS    mandatory
--		DESCRIPTION
--			"Units = pps"
--		::= { swhCountersRatesEntry 12 }

	swhCountersRatesRxAlignError OBJECT-TYPE
		SYNTAX    Counter
		ACCESS    read-only
		STATUS    mandatory
		DESCRIPTION
			"Units = pps"
		::= { swhCountersRatesEntry 13 }

	swhCountersRatesRxUndersizeFrames OBJECT-TYPE
		SYNTAX    Counter
		ACCESS    read-only
		STATUS    mandatory
		DESCRIPTION
			"Units = pps"
		::= { swhCountersRatesEntry 14 }

	swhCountersRatesRxOversizeFrames OBJECT-TYPE
		SYNTAX    Counter
		ACCESS    read-only
		STATUS    mandatory
		DESCRIPTION
			"Units = pps
			Rate of received packets with size over Jumbo Size."
		::= { swhCountersRatesEntry 15 }

	swhCountersRatesRxJabbers OBJECT-TYPE
		SYNTAX    Counter
		ACCESS    read-only
		STATUS    mandatory
		DESCRIPTION
			"Units = pps"
		::= { swhCountersRatesEntry 16 }

	swhCountersRatesRxDroppedFrames OBJECT-TYPE
		SYNTAX    Counter
		ACCESS    read-only
		STATUS    mandatory
		DESCRIPTION
			"Unit = pps
			Rate of received frames dropped. 
			(Drop Reason: incorrect VLAN; transmission rate over limitation; configured filtering rules; or no forwarding destination after receiving)"
		::= { swhCountersRatesEntry 17 }

	swhCountersRatesTxDroppedFrames OBJECT-TYPE
		SYNTAX    Counter
		ACCESS    read-only
		STATUS    mandatory
		DESCRIPTION
			"Units = pps"
		::= { swhCountersRatesEntry 18 }

--	swhCountersRatesTxLateCollision OBJECT-TYPE
--		SYNTAX    Counter
--		ACCESS    read-only
--		STATUS    mandatory
--		DESCRIPTION
--			""
--		::= { swhCountersRatesEntry 19 }

--	swhCountersRatesTxDeferred OBJECT-TYPE
--		SYNTAX    Counter
--		ACCESS    read-only
--		STATUS    mandatory
--		DESCRIPTION
--			""
--		::= { swhCountersRatesEntry 20 }

--	swhCountersRatesTxTotalCollision OBJECT-TYPE
--		SYNTAX    Counter
--		ACCESS    read-only
--		STATUS    mandatory
--		DESCRIPTION
--			""
--		::= { swhCountersRatesEntry 21 }

	swhCountersRatesRxFrames64 OBJECT-TYPE
		SYNTAX    Counter
		ACCESS    read-only
		STATUS    mandatory
		DESCRIPTION
			"Units = pps"
		::= { swhCountersRatesEntry 22 }

	swhCountersRatesRxFrames65to127 OBJECT-TYPE
		SYNTAX    Counter
		ACCESS    read-only
		STATUS    mandatory
		DESCRIPTION
			"Units = pps"
		::= { swhCountersRatesEntry 23 }

	swhCountersRatesRxFrames128to255 OBJECT-TYPE
		SYNTAX    Counter
		ACCESS    read-only
		STATUS    mandatory
		DESCRIPTION
			"Units = pps"
		::= { swhCountersRatesEntry 24 }

	swhCountersRatesRxFrames256to511 OBJECT-TYPE
		SYNTAX    Counter
		ACCESS    read-only
		STATUS    mandatory
		DESCRIPTION
			"Units = pps"
		::= { swhCountersRatesEntry 25 }

	swhCountersRatesRxFrames512to1023 OBJECT-TYPE
		SYNTAX    Counter
		ACCESS    read-only
		STATUS    mandatory
		DESCRIPTION
			"Units = pps"
		::= { swhCountersRatesEntry 26 }

--	swhCountersRatesRxFrames1024toMaxSize OBJECT-TYPE
--		SYNTAX    Counter
--		ACCESS    read-only
--		STATUS    mandatory
--		DESCRIPTION
--			""
--		::= { swhCountersRatesEntry 27 }

	swhCountersRatesRxUnicastFrames OBJECT-TYPE
		SYNTAX    Counter
		ACCESS    read-only
		STATUS    mandatory
		DESCRIPTION
			"Units = pps"
		::= { swhCountersRatesEntry 28 }

	swhCountersRatesRxMulticastFrames OBJECT-TYPE
		SYNTAX    Counter
		ACCESS    read-only
		STATUS    mandatory
		DESCRIPTION
			"Units = pps"
		::= { swhCountersRatesEntry 29 }

	swhCountersRatesRxBroadcastFrames OBJECT-TYPE
		SYNTAX    Counter
		ACCESS    read-only
		STATUS    mandatory
		DESCRIPTION
			"Units = pps"
		::= { swhCountersRatesEntry 30 }

	swhCountersRatesTxUnicastFrames OBJECT-TYPE
		SYNTAX    Counter
		ACCESS    read-only
		STATUS    mandatory
		DESCRIPTION
			"Units = pps"
		::= { swhCountersRatesEntry 31 }

	swhCountersRatesTxMulticastFrames OBJECT-TYPE
		SYNTAX    Counter
		ACCESS    read-only
		STATUS    mandatory
		DESCRIPTION
			"Units = pps"
		::= { swhCountersRatesEntry 32 }

	swhCountersRatesTxBroadcastFrames OBJECT-TYPE
		SYNTAX    Counter
		ACCESS    read-only
		STATUS    mandatory
		DESCRIPTION
			"Units = pps"
		::= { swhCountersRatesEntry 33 }

--	swhCountersRatesRxTotalErrors OBJECT-TYPE
--		SYNTAX    Counter
--		ACCESS    read-only
--		STATUS    mandatory
--		DESCRIPTION
--			""
--		::= { swhCountersRatesEntry 34 }

--	swhCountersRatesTxTotalErrors OBJECT-TYPE
--		SYNTAX    Counter
--		ACCESS    read-only
--		STATUS    mandatory
--		DESCRIPTION
--			""
--		::= { swhCountersRatesEntry 35 }

--	swhCountersRatesTxTotalCollisions OBJECT-TYPE
--		SYNTAX    Counter
--		ACCESS    read-only
--		STATUS    mandatory
--		DESCRIPTION
--			""
--		::= { swhCountersRatesEntry 36 }

--	swhCountersRatesRxCRCAlignError OBJECT-TYPE
--		SYNTAX    Counter
--		ACCESS    read-only
--		STATUS    mandatory
--		DESCRIPTION
--			""
--		::= { swhCountersRatesEntry 37 }

	swhCountersRatesTxCollision OBJECT-TYPE
		SYNTAX    Counter
		ACCESS    read-only
		STATUS    mandatory
		DESCRIPTION
			"Units = pps"
		::= { swhCountersRatesEntry 38 }

	swhCountersRatesTotalErrors OBJECT-TYPE
		SYNTAX    Counter
		ACCESS    read-only
		STATUS    mandatory
		DESCRIPTION
			"Units = pps"
		::= { swhCountersRatesEntry 39 }

	swhCountersRatesRxFrames1024to1518 OBJECT-TYPE
		SYNTAX    Counter
		ACCESS    read-only
		STATUS    mandatory
		DESCRIPTION
			"Units = pps"
		::= { swhCountersRatesEntry 40 }

	swhCountersRatesRxFrames1519toMaxSize OBJECT-TYPE
		SYNTAX    Counter
		ACCESS    read-only
		STATUS    mandatory
		DESCRIPTION
			"Units = pps
			Rate of received packets with size between 1519 to Jumbo Size."
		::= { swhCountersRatesEntry 41 }

	swhCountersRatesTotalErrorsExcludeDrop OBJECT-TYPE
		SYNTAX    Counter
		ACCESS    read-only
		STATUS    mandatory
		DESCRIPTION
			"Units = pps"
		::= { swhCountersRatesEntry 43 }

--  Counters Rates Traffic

	SwhCountersRatesTraffic ::=
		SEQUENCE {
			swhCountersRatesIndex
				INTEGER,
			swhCountersRatesBytesReceived
				Counter,
			swhCountersRatesFramesReceived
				Counter,
			swhCountersRatesReceivedUtilization
				DisplayString,
			swhCountersRatesBytesSent
				Counter,
			swhCountersRatesFramesSent
				Counter,
			swhCountersRatesSentUtilization
				DisplayString,
			swhCountersRatesTotalBytes
				Counter,
			swhCountersRatesTotalUtilization
				DisplayString
		}

--  Counters Rates Error

	SwhCountersRatesError ::=
		SEQUENCE {
			swhCountersRatesIndex
				INTEGER,
		--	swhCountersRatesRxCRCAlignError
		--		Counter,
			swhCountersRatesRxCRCError
				Counter,
			swhCountersRatesRxAlignError
				Counter,
			swhCountersRatesRxUndersizeFrames
				Counter,
			swhCountersRatesRxFragments
				Counter,
			swhCountersRatesRxJabbers
				Counter,
			swhCountersRatesRxOversizeFrames
				Counter,
			swhCountersRatesRxDroppedFrames
				Counter,
			swhCountersRatesTxCollision
				Counter,
			swhCountersRatesTxDroppedFrames
				Counter,
			swhCountersRatesTotalErrors
				Counter,
			swhCountersRatesTotalErrorsExcludeDrop
				Counter
		}

--  Counters Rates Analysis

	SwhCountersRatesAnalysis ::=
		SEQUENCE {
			swhCountersRatesIndex
				INTEGER,
			swhCountersRatesRxFrames64
				Counter,
			swhCountersRatesRxFrames65to127
				Counter,
			swhCountersRatesRxFrames128to255
				Counter,
			swhCountersRatesRxFrames256to511
				Counter,
			swhCountersRatesRxFrames512to1023
				Counter,
			swhCountersRatesRxFrames1024to1518
				Counter,
			swhCountersRatesRxFrames1519toMaxSize
				Counter,
			swhCountersRatesTxUnicastFrames
				Counter,
			swhCountersRatesTxMulticastFrames
				Counter,
			swhCountersRatesTxBroadcastFrames
				Counter,
			swhCountersRatesRxUnicastFrames
				Counter,
			swhCountersRatesRxMulticastFrames
				Counter,
			swhCountersRatesRxBroadcastFrames
				Counter
		}


-- SwitchMonitor(5).PortCountersEvents(6)

	swhCountersEventsTable OBJECT-TYPE
		SYNTAX    SEQUENCE OF SwhCountersEventsEntry
		ACCESS    not-accessible
		STATUS    mandatory
		DESCRIPTION
			"Table of Port counters events."
		::= { swhPortCountersEvents 1 }

	swhCountersEventsClearCountersOfAllPort OBJECT-TYPE
		SYNTAX    INTEGER { normal(0), clear(1) }
		ACCESS    read-write
		STATUS    mandatory
		DESCRIPTION
			"Clear Counters of All Port"
		::= { swhPortCountersEvents 2  }

	-- Table Entry
	swhCountersEventsEntry OBJECT-TYPE
		SYNTAX    SwhCountersEventsEntry
		ACCESS    not-accessible
		STATUS    mandatory
		DESCRIPTION
			"An entry in the table, containing information
			about Port counter events mode."
		INDEX    { swhCountersEventsIndex }
		::= { swhCountersEventsTable 1 }

	SwhCountersEventsEntry ::=
		SEQUENCE {
			swhCountersEventsIndex
				INTEGER,
			swhCountersEventsBytesReceived
				Counter64,
			swhCountersEventsFramesReceived
				Counter64,
			swhCountersEventsBytesSent
				Counter64,
			swhCountersEventsFramesSent
				Counter64,
			swhCountersEventsTotalBytes
				Counter64,
		--	swhCountersEventsRxCRCAlignError
		--		Counter64,
			swhCountersEventsRxCRCError
				Counter64,
			swhCountersEventsRxAlignError
				Counter64,
			swhCountersEventsRxUndersizeFrames
				Counter64,
			swhCountersEventsRxFragments
				Counter64,
			swhCountersEventsRxJabbers
				Counter64,
			swhCountersEventsRxOversizeFrames
				Counter64,
			swhCountersEventsRxDroppedFrames
				Counter64,
			swhCountersEventsTxCollision
				Counter64,
			swhCountersEventsTxDroppedFrames
				Counter64,
			swhCountersEventsRxFrames64
				Counter64,
			swhCountersEventsRxFrames65to127
				Counter64,
			swhCountersEventsRxFrames128to255
				Counter64,
			swhCountersEventsRxFrames256to511
				Counter64,
			swhCountersEventsRxFrames512to1023
				Counter64,
			swhCountersEventsRxFrames1024to1518
				Counter64,
			swhCountersEventsRxFrames1519toMaxSize
				Counter64,
			swhCountersEventsTxUnicastFrames
				Counter64,
			swhCountersEventsTxMulticastFrames
				Counter64,
			swhCountersEventsTxBroadcastFrames
				Counter64,
			swhCountersEventsRxUnicastFrames
				Counter64,
			swhCountersEventsRxMulticastFrames
				Counter64,
			swhCountersEventsRxBroadcastFrames
				Counter64,
		--	swhClearCountersOfThisModule
		--		INTEGER,
			swhCountersEventsTotalErrors
				Counter64,
			swhCountersEventsTotalErrorsExcludeDrop
				Counter64
		--	swhCountersEventsRxFilteredFrames
		--		Counter64,
		--	swhCountersEventsTxLateCollision
		--		Counter64,
		--	swhCountersEventsTxDeferred
		--		Counter64,
		--	swhCountersEventsTxTotalCollision
		--		Counter64,
		--	swhCountersEventsRxFrames1024toMaxSize
		--		Counter64,
		--	swhCountersEventsRxUnicastFrames
		--		Counter64,
		--	swhCountersEventsTxUnicastFrames
		--		Counter64,
		--	swhCountersEventsRxTotalErrors
		--		Counter64,
		--	swhCountersEventsTxTotalErrors
		--		Counter64,
		--	swhCountersEventsTxTotalCollisions
		--		Counter64
		}

	swhCountersEventsIndex OBJECT-TYPE
		SYNTAX    INTEGER (0..2147483647)
		ACCESS    not-accessible
		STATUS    mandatory
		DESCRIPTION
			"A unique value for each Port."
		::= { swhCountersEventsEntry 1 }

	swhCountersEventsBytesReceived OBJECT-TYPE
		SYNTAX    Counter64
		ACCESS    read-only
		STATUS    mandatory
		DESCRIPTION
			""
		::= { swhCountersEventsEntry 2 }

	swhCountersEventsFramesReceived OBJECT-TYPE
		SYNTAX    Counter64
		ACCESS    read-only
		STATUS    mandatory
		DESCRIPTION
			""
		::= { swhCountersEventsEntry 3 }

--	swhCountersEventsReceivedUtilization OBJECT-TYPE
--		SYNTAX    DisplayString
--		ACCESS    read-only
--		STATUS    mandatory
--		DESCRIPTION
--			""
--		::= { swhCountersEventsEntry 4 }

	swhCountersEventsBytesSent OBJECT-TYPE
		SYNTAX    Counter64
		ACCESS    read-only
		STATUS    mandatory
		DESCRIPTION
			""
		::= { swhCountersEventsEntry 5 }

	swhCountersEventsFramesSent OBJECT-TYPE
		SYNTAX    Counter64
		ACCESS    read-only
		STATUS    mandatory
		DESCRIPTION
			""
		::= { swhCountersEventsEntry 6 }

--	swhCountersEventsSentUtilization OBJECT-TYPE
--		SYNTAX    DisplayString
--		ACCESS    read-only
--		STATUS    mandatory
--		DESCRIPTION
--			""
--		::= { swhCountersEventsEntry 7 }

	swhCountersEventsTotalBytes OBJECT-TYPE
		SYNTAX    Counter64
		ACCESS    read-only
		STATUS    mandatory
		DESCRIPTION
			""
		::= { swhCountersEventsEntry 8 }

--	swhCountersEventsTotalUtilization OBJECT-TYPE
--		SYNTAX    DisplayString
--		ACCESS    read-only
--		STATUS    mandatory
--		DESCRIPTION
--			""
--		::= { swhCountersEventsEntry 9 }

	swhCountersEventsRxCRCError OBJECT-TYPE
		SYNTAX    Counter64
		ACCESS    read-only
		STATUS    mandatory
		DESCRIPTION
			""
		::= { swhCountersEventsEntry 10 }

	swhCountersEventsRxFragments OBJECT-TYPE
		SYNTAX    Counter64
		ACCESS    read-only
		STATUS    mandatory
		DESCRIPTION
			""
		::= { swhCountersEventsEntry 11 }

	swhCountersEventsRxFilteredFrames OBJECT-TYPE
		SYNTAX    Counter64
		ACCESS    read-only
		STATUS    mandatory
		DESCRIPTION
			""
		::= { swhCountersEventsEntry 12 }

	swhCountersEventsRxAlignError OBJECT-TYPE
		SYNTAX    Counter64
		ACCESS    read-only
		STATUS    mandatory
		DESCRIPTION
			""
		::= { swhCountersEventsEntry 13 }

	swhCountersEventsRxUndersizeFrames OBJECT-TYPE
		SYNTAX    Counter64
		ACCESS    read-only
		STATUS    mandatory
		DESCRIPTION
			""
		::= { swhCountersEventsEntry 14 }

	swhCountersEventsRxOversizeFrames OBJECT-TYPE
		SYNTAX    Counter64
		ACCESS    read-only
		STATUS    mandatory
		DESCRIPTION
			"Counter of event of received packets with size over Jumbo Size."
		::= { swhCountersEventsEntry 15 }

	swhCountersEventsRxJabbers OBJECT-TYPE
		SYNTAX    Counter64
		ACCESS    read-only
		STATUS    mandatory
		DESCRIPTION
			""
		::= { swhCountersEventsEntry 16 }

	swhCountersEventsRxDroppedFrames OBJECT-TYPE
		SYNTAX    Counter64
		ACCESS    read-only
		STATUS    mandatory
		DESCRIPTION
			"Counter of event of received frames dropped.
			(Drop Reason: incorrect VLAN; transmission rate over limitation; configured filtering rules; or no forwarding destination after receiving)"
		::= { swhCountersEventsEntry 17 }

	swhCountersEventsTxDroppedFrames OBJECT-TYPE
		SYNTAX    Counter64
		ACCESS    read-only
		STATUS    mandatory
		DESCRIPTION
			""
		::= { swhCountersEventsEntry 18 }

	swhCountersEventsTxLateCollision OBJECT-TYPE
		SYNTAX    Counter64
		ACCESS    read-only
		STATUS    mandatory
		DESCRIPTION
			""
		::= { swhCountersEventsEntry 19 }

	swhCountersEventsTxDeferred OBJECT-TYPE
		SYNTAX    Counter64
		ACCESS    read-only
		STATUS    mandatory
		DESCRIPTION
			""
		::= { swhCountersEventsEntry 20 }

--	swhCountersEventsTxTotalCollision OBJECT-TYPE
--		SYNTAX    Counter64
--		ACCESS    read-only
--		STATUS    mandatory
--		DESCRIPTION
--			""
--		::= { swhCountersEventsEntry 21 }

	swhCountersEventsRxFrames64 OBJECT-TYPE
		SYNTAX    Counter64
		ACCESS    read-only
		STATUS    mandatory
		DESCRIPTION
			""
		::= { swhCountersEventsEntry 22 }

	swhCountersEventsRxFrames65to127 OBJECT-TYPE
		SYNTAX    Counter64
		ACCESS    read-only
		STATUS    mandatory
		DESCRIPTION
			""
		::= { swhCountersEventsEntry 23 }

	swhCountersEventsRxFrames128to255 OBJECT-TYPE
		SYNTAX    Counter64
		ACCESS    read-only
		STATUS    mandatory
		DESCRIPTION
			""
		::= { swhCountersEventsEntry 24 }

	swhCountersEventsRxFrames256to511 OBJECT-TYPE
		SYNTAX    Counter64
		ACCESS    read-only
		STATUS    mandatory
		DESCRIPTION
			""
		::= { swhCountersEventsEntry 25 }

	swhCountersEventsRxFrames512to1023 OBJECT-TYPE
		SYNTAX    Counter64
		ACCESS    read-only
		STATUS    mandatory
		DESCRIPTION
			""
		::= { swhCountersEventsEntry 26 }

--	swhCountersEventsRxFrames1024toMaxSize OBJECT-TYPE
--		SYNTAX    Counter64
--		ACCESS    read-only
--		STATUS    mandatory
--		DESCRIPTION
--			""
--		::= { swhCountersEventsEntry 27 }

	swhCountersEventsRxUnicastFrames OBJECT-TYPE
		SYNTAX    Counter64
		ACCESS    read-only
		STATUS    mandatory
		DESCRIPTION
			""
		::= { swhCountersEventsEntry 28 }

	swhCountersEventsRxMulticastFrames OBJECT-TYPE
		SYNTAX    Counter64
		ACCESS    read-only
		STATUS    mandatory
		DESCRIPTION
			""
		::= { swhCountersEventsEntry 29 }

	swhCountersEventsRxBroadcastFrames OBJECT-TYPE
		SYNTAX    Counter64
		ACCESS    read-only
		STATUS    mandatory
		DESCRIPTION
			""
		::= { swhCountersEventsEntry 30 }

	swhCountersEventsTxUnicastFrames OBJECT-TYPE
		SYNTAX    Counter64
		ACCESS    read-only
		STATUS    mandatory
		DESCRIPTION
			""
		::= { swhCountersEventsEntry 31 }

	swhCountersEventsTxMulticastFrames OBJECT-TYPE
		SYNTAX    Counter64
		ACCESS    read-only
		STATUS    mandatory
		DESCRIPTION
			""
		::= { swhCountersEventsEntry 32 }

	swhCountersEventsTxBroadcastFrames OBJECT-TYPE
		SYNTAX    Counter64
		ACCESS    read-only
		STATUS    mandatory
		DESCRIPTION
			""
		::= { swhCountersEventsEntry 33 }

--	swhClearCountersOfThisModule OBJECT-TYPE
--		SYNTAX    INTEGER { normal(0), clear(1) }
--		ACCESS    write-only
--		STATUS    mandatory
--		DESCRIPTION
--			"Clear Counters of This module"
--		::= { swhCountersEventsEntry 34  }

--	swhCountersEventsRxTotalErrors OBJECT-TYPE
--		SYNTAX    Counter64
--		ACCESS    read-only
--		STATUS    mandatory
--		DESCRIPTION
--			""
--		::= { swhCountersEventsEntry 35 }

--	swhCountersEventsTxTotalErrors OBJECT-TYPE
--		SYNTAX    Counter64
--		ACCESS    read-only
--		STATUS    mandatory
--		DESCRIPTION
--			""
--		::= { swhCountersEventsEntry 36 }

--	swhCountersEventsTxTotalCollisions OBJECT-TYPE
--		SYNTAX    Counter64
--		ACCESS    read-only
--		STATUS    mandatory
--		DESCRIPTION
--			""
--		::= { swhCountersEventsEntry 37 }

--	swhCountersEventsRxCRCAlignError OBJECT-TYPE
--		SYNTAX    Counter64
--		ACCESS    read-only
--		STATUS    mandatory
--		DESCRIPTION
--			""
--		::= { swhCountersEventsEntry 38 }

	swhCountersEventsTxCollision OBJECT-TYPE
		SYNTAX    Counter64
		ACCESS    read-only
		STATUS    mandatory
		DESCRIPTION
			""
		::= { swhCountersEventsEntry 39 }

	swhCountersEventsRxFrames1024to1518 OBJECT-TYPE
		SYNTAX    Counter64
		ACCESS    read-only
		STATUS    mandatory
		DESCRIPTION
			""
		::= { swhCountersEventsEntry 40 }

	swhCountersEventsRxFrames1519toMaxSize OBJECT-TYPE
		SYNTAX    Counter64
		ACCESS    read-only
		STATUS    mandatory
		DESCRIPTION
			"Counter of event of received packets with size between 1519 to Jumbo Size."
		::= { swhCountersEventsEntry 41 }

	swhCountersEventsTotalErrors  OBJECT-TYPE
		SYNTAX    Counter64
		ACCESS    read-only
		STATUS    mandatory
		DESCRIPTION
			""
		::= { swhCountersEventsEntry 42 }

	swhCountersEventsTotalErrorsExcludeDrop  OBJECT-TYPE
		SYNTAX    Counter64
		ACCESS    read-only
		STATUS    mandatory
		DESCRIPTION
			""
		::= { swhCountersEventsEntry 44 }

--  Counters Events Traffic

	SwhCountersEventsTraffic ::=
		SEQUENCE {
			swhCountersEventsIndex
				INTEGER,
			swhCountersEventsBytesReceived
				Counter64,
			swhCountersEventsFramesReceived
				Counter64,
			swhCountersEventsBytesSent
				Counter64,
			swhCountersEventsFramesSent
				Counter64,
			swhCountersEventsTotalBytes
				Counter64
		--	swhClearCountersOfThisModule
		--		INTEGER
		}

--  Counters Events Error

	SwhCountersEventsError ::=
		SEQUENCE {
			swhCountersEventsIndex
				INTEGER,
		--	swhCountersEventsRxCRCAlignError
		--		Counter64,
			swhCountersEventsRxCRCError
				Counter64,
			swhCountersEventsRxAlignError
				Counter64,
			swhCountersEventsRxUndersizeFrames
				Counter64,
			swhCountersEventsRxFragments
				Counter64,
			swhCountersEventsRxJabbers
				Counter64,
			swhCountersEventsRxOversizeFrames
				Counter64,
			swhCountersEventsRxDroppedFrames
				Counter64,
			swhCountersEventsTxCollision
				Counter64,
			swhCountersEventsTxDroppedFrames
				Counter64,
			swhCountersEventsTotalErrors
				Counter64,
			swhCountersEventsTotalErrorsExcludeDrop
				Counter64
		--	swhClearCountersOfThisModule
		--		INTEGER
		}

--  Counters Events Analysis

	SwhCountersEventsAnalysis ::=
		SEQUENCE {
			swhCountersEventsIndex
				INTEGER,
			swhCountersEventsRxFrames64
				Counter64,
			swhCountersEventsRxFrames65to127
				Counter64,
			swhCountersEventsRxFrames128to255
				Counter64,
			swhCountersEventsRxFrames256to511
				Counter64,
			swhCountersEventsRxFrames512to1023
				Counter64,
			swhCountersEventsRxFrames1024to1518
				Counter64,
			swhCountersEventsRxFrames1519toMaxSize
				Counter64,
			swhCountersEventsTxUnicastFrames
				Counter64,
			swhCountersEventsTxMulticastFrames
				Counter64,
			swhCountersEventsTxBroadcastFrames
				Counter64,
			swhCountersEventsRxUnicastFrames
				Counter64,
			swhCountersEventsRxMulticastFrames
				Counter64,
			swhCountersEventsRxBroadcastFrames
				Counter64
		--	swhClearCountersOfThisModule
		--		INTEGER
		}


-- SwitchMonitor(5).MacAddressTable(7)

	swhMacAddressPortSelect OBJECT-TYPE
		SYNTAX    INTEGER { all(0),
		                    port01(1),
		                    port02(2),
		                    port03(3),
		                    port04(4),
		                    port05(5),
		                    port06(6),
		                    cpu(7)
		                    }
		ACCESS    read-write
		STATUS    mandatory
		DESCRIPTION
			"Display mac address of the port which is selected."
		::= { swhMacAddressTable 1 }

	swhMacAddressVLANSelect OBJECT-TYPE
		SYNTAX    INTEGER (0..2147483647)
		ACCESS    read-write
		STATUS    mandatory
		DESCRIPTION
			"Display mac address of the vlan which is selected."
		::= { swhMacAddressTable 10 }

	swhMacAddressMACSelect OBJECT-TYPE
		SYNTAX    DisplayString
		ACCESS    read-write
		STATUS    mandatory
		DESCRIPTION
			"Display mac address of the mac which is selected."
		::= { swhMacAddressTable 11 }

	swhMacAddressPageSelect OBJECT-TYPE
		SYNTAX    INTEGER (0..2147483647)
		ACCESS    read-write
		STATUS    mandatory
		DESCRIPTION
			"Display mac address of the page which is selected."
		::= { swhMacAddressTable 9 }

	swhMacAddressUpdate OBJECT-TYPE
		SYNTAX    INTEGER { normal(0), update(1) }
		ACCESS    read-write
		STATUS    mandatory
		DESCRIPTION
			"Update mac address table."
		::= { swhMacAddressTable 3 }

	swhMacAddressClear OBJECT-TYPE
		SYNTAX    INTEGER { normal(0), clear(1) }
		ACCESS    read-write
		STATUS    mandatory
		DESCRIPTION
			"Clear mac address table."
		::= { swhMacAddressTable 2 }

	swhMacAddressTotal OBJECT-TYPE
		SYNTAX    INTEGER (0..2147483647)
		ACCESS    read-only
		STATUS    mandatory
		DESCRIPTION
			"The amount of total learned mac address."
		::= { swhMacAddressTable 4 }

	swhMacAddressState OBJECT-TYPE
		SYNTAX    DisplayString
		ACCESS    read-only
		STATUS    mandatory
		DESCRIPTION
			"The state of mac address table."
		::= { swhMacAddressTable 5 }

	swhMacAddressCapacity OBJECT-TYPE
		SYNTAX    INTEGER (0..2147483647)
		ACCESS    read-only
		STATUS    mandatory
		DESCRIPTION
			"Capacity"
		::= { swhMacAddressTable 20 }

	swhMacAddressFree OBJECT-TYPE
		SYNTAX    INTEGER (0..2147483647)
		ACCESS    read-only
		STATUS    mandatory
		DESCRIPTION
			"Free"
		::= { swhMacAddressTable 21 }

	swhMacAddressUsed OBJECT-TYPE
		SYNTAX    INTEGER (0..2147483647)
		ACCESS    read-only
		STATUS    mandatory
		DESCRIPTION
			"Used"
		::= { swhMacAddressTable 22 }

	swhMacAddressDynamic OBJECT-TYPE
		SYNTAX    INTEGER (0..2147483647)
		ACCESS    read-only
		STATUS    mandatory
		DESCRIPTION
			"Dynamic"
		::= { swhMacAddressTable 24 }

	swhMacAddressStatic OBJECT-TYPE
		SYNTAX    INTEGER (0..2147483647)
		ACCESS    read-only
		STATUS    mandatory
		DESCRIPTION
			"Static"
		::= { swhMacAddressTable 25 }

	swhMacAddressInternal OBJECT-TYPE
		SYNTAX    INTEGER (0..2147483647)
		ACCESS    read-only
		STATUS    mandatory
		DESCRIPTION
			"Internal"
		::= { swhMacAddressTable 26 }


-- SwitchMonitor(5).MacAddressTable(7).MacTable(6)

	swhMacTable OBJECT-TYPE
		SYNTAX    SEQUENCE OF SwhMacTableEntry
		ACCESS    not-accessible
		STATUS    mandatory
		DESCRIPTION
			"Table of Mac Address."
		::= { swhMacAddressTable 6 }

	-- Table Entry
	swhMacTableEntry OBJECT-TYPE
		SYNTAX    SwhMacTableEntry
		ACCESS    not-accessible
		STATUS    mandatory
		DESCRIPTION
			"An entry in the table, containing information
			about mac address table"
		INDEX    { swhMacTableIndex }
		::= { swhMacTable 1 }

	SwhMacTableEntry ::=
		SEQUENCE {
			swhMacTableIndex
				INTEGER,
			swhMacTableType
				DisplayString,
			swhMacTableAddr
				MacAddress,
			swhMacTableVID
				INTEGER,
			swhMacTablePort
				DisplayString
		}

	swhMacTableIndex OBJECT-TYPE
		SYNTAX    INTEGER (0..2147483647)
		ACCESS    not-accessible
		STATUS    mandatory
		DESCRIPTION
			"A unique value for mac address index."
		::= { swhMacTableEntry 1 }

	swhMacTableAddr OBJECT-TYPE
		SYNTAX    MacAddress
		ACCESS    read-only
		STATUS    mandatory
		DESCRIPTION
			"MAC address learned."
		::= { swhMacTableEntry 2 }

	swhMacTableVID OBJECT-TYPE
		SYNTAX    INTEGER 
		ACCESS    read-only
		STATUS    mandatory
		DESCRIPTION
			"MAC address learned from which vlan id."
		::= { swhMacTableEntry 3 }

	swhMacTablePort OBJECT-TYPE
		SYNTAX    DisplayString
		ACCESS    read-only
		STATUS    mandatory
		DESCRIPTION
			"MAC address learned from which port."
		::= { swhMacTableEntry 4 }

	swhMacTableType OBJECT-TYPE
		SYNTAX    DisplayString
		ACCESS    read-only
		STATUS    mandatory
		DESCRIPTION
			"MAC address learning type."
		::= { swhMacTableEntry 5 }


-- SwitchMonitor(5).RSTPBridgeOverview(10)

	--swhRSTPBridgeTable OBJECT-TYPE
	--	SYNTAX    SEQUENCE OF SwhRSTPBridgeEntry
	--	ACCESS    not-accessible
	--	STATUS    mandatory
	--	DESCRIPTION
	--		"Table of RSTP Bridge Overview."
	--	::= { swhRSTPBridgeOverview 7 }

	-- Table Entry
	--swhRSTPBridgeEntry OBJECT-TYPE
	--	SYNTAX    SwhRSTPBridgeEntry
	--	ACCESS    not-accessible
	--	STATUS    mandatory
	--	DESCRIPTION
	--		"An entry in the table, containing information
	--		about RSTP Bridge mode."
	--	INDEX    { swhRSTPBridgeIndex }
	--	::= { swhRSTPBridgeTable 1 }

	--SwhRSTPBridgeEntry ::=
	--	SEQUENCE {
	--		swhRSTPBridgeIndex
	--			INTEGER,
		--	swhRSTPBridgeVLANID
		--		INTEGER,
	--		swhRSTPBridgeBridgeID
	--			DisplayString,
	--		swhRSTPBridgeMaxAge
	--			INTEGER,
	--		swhRSTPBridgeHelloTime
	--			INTEGER,
	--		swhRSTPBridgeFwdDelay
	--			INTEGER,
	--		swhRSTPBridgeTopology
	--			INTEGER,
		--	swhRSTPBridgeTopologyCount
		--		INTEGER,
		--	swhRSTPBridgeLastTopology
		--		INTEGER,
	--		swhRSTPBridgeRootID
	--			DisplayString,
	--		swhRSTPBridgeRootPort
	--			DisplayString
		--	swhRSTPBridgeViaGroup
		--		INTEGER,
		--	swhRSTPBridgeViaPort
		--		INTEGER
	--	}

	--swhRSTPBridgeIndex OBJECT-TYPE
	--	SYNTAX    INTEGER (0..2147483647)
	--	ACCESS    not-accessible
	--	STATUS    mandatory
	--	DESCRIPTION
	--		"A unique value for each Port."
	--	::= { swhRSTPBridgeEntry 1 }

	--swhRSTPBridgeVLANID OBJECT-TYPE
	--	SYNTAX    INTEGER
	--	ACCESS    read-only
	--	STATUS    mandatory
	--	DESCRIPTION
	--		"VLAN ID"
	--	::= { swhRSTPBridgeEntry 2 }

	--swhRSTPBridgeBridgeID OBJECT-TYPE
	--	SYNTAX    DisplayString
	--	ACCESS    read-only
	--	STATUS    mandatory
	--	DESCRIPTION
	--		"Bridge ID"
	--	::= { swhRSTPBridgeEntry 3 }

	--swhRSTPBridgeMaxAge OBJECT-TYPE
	--	SYNTAX    INTEGER
	--	ACCESS    read-only
	--	STATUS    mandatory
	--	DESCRIPTION
	--		"Max Age"
	--	::= { swhRSTPBridgeEntry 4 }

	--swhRSTPBridgeHelloTime OBJECT-TYPE
	--	SYNTAX    INTEGER
	--	ACCESS    read-only
	--	STATUS    mandatory
	--	DESCRIPTION
	--		"Hello Time"
	--	::= { swhRSTPBridgeEntry 5 }

	--swhRSTPBridgeFwdDelay OBJECT-TYPE
	--	SYNTAX    INTEGER
	--	ACCESS    read-only
	--	STATUS    mandatory
	--	DESCRIPTION
	--		"Fwd Delay"
	--	::= { swhRSTPBridgeEntry 6 }

	--swhRSTPBridgeTopology OBJECT-TYPE
	--	SYNTAX    INTEGER { steady(0), changing(1) }
	--	ACCESS    read-only
	--	STATUS    mandatory
	--	DESCRIPTION
	--		"Topology"
	--	::= { swhRSTPBridgeEntry 7 }

--	swhRSTPBridgeTopologyCount OBJECT-TYPE
--		SYNTAX    INTEGER
--		ACCESS    read-only
--		STATUS    mandatory
--		DESCRIPTION
--			"Topology Count"
--		::= { swhRSTPBridgeEntry 8 }

--	swhRSTPBridgeLastTopology OBJECT-TYPE
--		SYNTAX    INTEGER
--		ACCESS    read-only
--		STATUS    mandatory
--		DESCRIPTION
--			"Last Topology"
--		::= { swhRSTPBridgeEntry 9 }

	--swhRSTPBridgeRootID OBJECT-TYPE
	--	SYNTAX    DisplayString
	--	ACCESS    read-only
	--	STATUS    mandatory
	--	DESCRIPTION
	--		"Root ID"
	--	::= { swhRSTPBridgeEntry 10 }

--	swhRSTPBridgeViaGroup OBJECT-TYPE
--		SYNTAX    INTEGER
--		ACCESS    read-only
--		STATUS    mandatory
--		DESCRIPTION
--			"Via Group"
--		::= { swhRSTPBridgeEntry 11 }

--	swhRSTPBridgeViaPort OBJECT-TYPE
--		SYNTAX    INTEGER
--		ACCESS    read-only
--		STATUS    mandatory
--		DESCRIPTION
--			"Via Port"
--		::= { swhRSTPBridgeEntry 12 }

	--swhRSTPBridgeRootPort OBJECT-TYPE
	--	SYNTAX    DisplayString
	--	ACCESS    read-only
	--	STATUS    mandatory
	--	DESCRIPTION
	--		"Root Port"
	--	::= { swhRSTPBridgeEntry 13 }


-- SwitchMonitor(5).LLDPStatus(11)

--	swhLLDPStatusTable OBJECT-TYPE
--		SYNTAX    SEQUENCE OF SwhLLDPStatusTableEntry
--		ACCESS    not-accessible
--		STATUS    mandatory
--		DESCRIPTION
--			"Table of LLDP Status."
--		::= { swhLLDPStatus 4 }
--
	-- Table Entry
--	SwhLLDPStatusTableEntry OBJECT-TYPE
--		SYNTAX    SwhLLDPStatusTableEntry
--		ACCESS    not-accessible
--		STATUS    mandatory
--		DESCRIPTION
--			"An entry in the table, containing information
--			 about LLDP Status table"
--		INDEX    { swhLLDPStatusTableIndex }
--		::= { swhLLDPStatusTable 1 }
--
--	SwhLLDPStatusTableEntry ::=
--		SEQUENCE {
--			swhLLDPStatusTableIndex
--				INTEGER,
--			swhLLDPStatusTableChassisID
--				DisplayString,
--			swhLLDPStatusTableRemotePort
--				DisplayString,
--			swhLLDPStatusTableSystemName
--				DisplayString,
--			swhLLDPStatusTablePortDescription
--				DisplayString,
--			swhLLDPStatusTableSystemCapabilities
--				DisplayString,
--			swhLLDPStatusTableManagement1Address
--				DisplayString,
--			swhLLDPStatusTableManagement2Address
--				DisplayString,
--			swhLLDPStatusTableManagement3Address
--				DisplayString,
--			swhLLDPStatusTableManagement4Address
--				DisplayString,
--			swhLLDPStatusTableManagement5Address
--				DisplayString
--		}
--
--	swhLLDPStatusTableIndex OBJECT-TYPE
--		SYNTAX    INTEGER (0..2147483647)
--		ACCESS    not-accessible
--		STATUS    mandatory
--		DESCRIPTION
--			"A unique value for Port index."
--		::= { swhLLDPStatusTableEntry 1 }
--
--	swhLLDPStatusTableChassisID OBJECT-TYPE
--		SYNTAX    DisplayString
--		ACCESS    read-only
--		STATUS    mandatory
--		DESCRIPTION
--			"Chassis ID."
--		::= { swhLLDPStatusTableEntry 3 }
--
--	swhLLDPStatusTableRemotePort OBJECT-TYPE
--		SYNTAX    DisplayString
--		ACCESS    read-only
--		STATUS    mandatory
--		DESCRIPTION
--			"Remote Port."
--		::= { swhLLDPStatusTableEntry 4 }
--
--	swhLLDPStatusTableSystemName OBJECT-TYPE
--		SYNTAX    DisplayString
--		ACCESS    read-only
--		STATUS    mandatory
--		DESCRIPTION
--			"System Name."
--		::= { swhLLDPStatusTableEntry 5 }
--
--	swhLLDPStatusTablePortDescription OBJECT-TYPE
--		SYNTAX    DisplayString
--		ACCESS    read-only
--		STATUS    mandatory
--		DESCRIPTION
--			"Port Description."
--		::= { swhLLDPStatusTableEntry 6 }
--
--	swhLLDPStatusTableSystemCapabilities OBJECT-TYPE
--		SYNTAX    DisplayString
--		ACCESS    read-only
--		STATUS    mandatory
--		DESCRIPTION
--			"System Capabilities."
--		::= { swhLLDPStatusTableEntry 7 }
--
--	swhLLDPStatusTableManagement1Address OBJECT-TYPE
--		SYNTAX    DisplayString
--		ACCESS    read-only
--		STATUS    mandatory
--		DESCRIPTION
--			"Management Address."
--		::= { swhLLDPStatusTableEntry 8 }
--
--	swhLLDPStatusTableManagement2Address OBJECT-TYPE
--		SYNTAX    DisplayString
--		ACCESS    read-only
--		STATUS    mandatory
--		DESCRIPTION
--			"Management Address."
--		::= { swhLLDPStatusTableEntry 9 }
--
--	swhLLDPStatusTableManagement3Address OBJECT-TYPE
--		SYNTAX    DisplayString
--		ACCESS    read-only
--		STATUS    mandatory
--		DESCRIPTION
--			"Management Address."
--		::= { swhLLDPStatusTableEntry 10 }
--
--	swhLLDPStatusTableManagement4Address OBJECT-TYPE
--		SYNTAX    DisplayString
--		ACCESS    read-only
--		STATUS    mandatory
--		DESCRIPTION
--			"Management Address."
--		::= { swhLLDPStatusTableEntry 11 }
--
--	swhLLDPStatusTableManagement5Address OBJECT-TYPE
--		SYNTAX    DisplayString
--		ACCESS    read-only
--		STATUS    mandatory
--		DESCRIPTION
--			"Management Address."
--		::= { swhLLDPStatusTableEntry 12 }
--

-- SwitchMonitor(5).RSTPPortStatus(14).RSTPPortStatusTable(1)

	--swhRSTPPortStatusTable OBJECT-TYPE
	--	SYNTAX    SEQUENCE OF SwhRSTPPortStatusEntry
	--	ACCESS    not-accessible
	--	STATUS    mandatory
	--	DESCRIPTION
	--		"Table of RSTP Port Status."
	--	::= { swhRSTPPortStatus 1 }

	-- Table Entry
	--swhRSTPPortStatusEntry OBJECT-TYPE
	--	SYNTAX    SwhRSTPPortStatusEntry
	--	ACCESS    not-accessible
	--	STATUS    mandatory
	--	DESCRIPTION
	--		"An entry in the table, containing information
	--		about RSTP Port Status mode."
	--	INDEX    { swhRSTPPortStatusIndex }
	--	::= { swhRSTPPortStatusTable 1 }

	--SwhRSTPPortStatusEntry ::=
	--	SEQUENCE {
	--		swhRSTPPortStatusIndex
	--			INTEGER,
	--		swhRSTPPortStatusPort
	--			DisplayString,
		--	swhRSTPPortStatusVLANID
		--		INTEGER,
	--		swhRSTPPortStatusPathCost
	--			INTEGER,
	--		swhRSTPPortStatusEdgePort
	--			INTEGER,
	--		swhRSTPPortStatusP2pPort
	--			INTEGER,
	--		swhRSTPPortStatusProtocol
	--			INTEGER,
	--		swhRSTPPortStatusRole
	--			INTEGER,
	--		swhRSTPPortStatusPortState
	--			INTEGER
	--	}

	--swhRSTPPortStatusIndex OBJECT-TYPE
	--	SYNTAX    INTEGER (0..2147483647)
	--	ACCESS    not-accessible
	--	STATUS    mandatory
	--	DESCRIPTION
	--		"A unique value for each Port."
	--	::= { swhRSTPPortStatusEntry 1 }

	--swhRSTPPortStatusVLANID OBJECT-TYPE
	--	SYNTAX    INTEGER
	--	ACCESS    read-only
	--	STATUS    mandatory
	--	DESCRIPTION
	--		"VLAN ID"
	--	::= { swhRSTPPortStatusEntry 2 }

	--swhRSTPPortStatusPathCost OBJECT-TYPE
	--	SYNTAX    INTEGER
	--	ACCESS    read-only
	--	STATUS    mandatory
	--	DESCRIPTION
	--		"Path Cost"
	--	::= { swhRSTPPortStatusEntry 3 }

	--swhRSTPPortStatusEdgePort OBJECT-TYPE
	--	SYNTAX    INTEGER { no(0), yes(1) }
	--	ACCESS    read-only
	--	STATUS    mandatory
	--	DESCRIPTION
	--		"Edge Port"
	--	::= { swhRSTPPortStatusEntry 4 }

	--swhRSTPPortStatusP2pPort OBJECT-TYPE
	--	SYNTAX    INTEGER { no(0), yes(1) }
	--	ACCESS    read-only
	--	STATUS    mandatory
	--	DESCRIPTION
	--		"P2p Port"
	--	::= { swhRSTPPortStatusEntry 5 }

	--swhRSTPPortStatusProtocol OBJECT-TYPE
	--	SYNTAX    INTEGER { rstp(0), stp(1) }
	--	ACCESS    read-only
	--	STATUS    mandatory
	--	DESCRIPTION
	--		"Protocol"
	--	::= { swhRSTPPortStatusEntry 6 }

	--swhRSTPPortStatusRole OBJECT-TYPE
	--	SYNTAX    INTEGER { disable(0), alternate(1), backup(2), root(3), designated(4), non-stp(5) }
	--	ACCESS    read-only
	--	STATUS    mandatory
	--	DESCRIPTION
	--		"Role"
	--	::= { swhRSTPPortStatusEntry 7 }

	--swhRSTPPortStatusPortState OBJECT-TYPE
	--	SYNTAX    INTEGER { disable(0), blocking(1), listening(2), learning(3), forwarding(4), non-stp(5) }
	--	ACCESS    read-only
	--	STATUS    mandatory
	--	DESCRIPTION
	--		"Port State"
	--	::= { swhRSTPPortStatusEntry 8 }

	--swhRSTPPortStatusPort OBJECT-TYPE
	--	SYNTAX    DisplayString
	--	ACCESS    read-only
	--	STATUS    mandatory
	--	DESCRIPTION
	--		"Port Name"
	--	::= { swhRSTPPortStatusEntry 9 }


-- SwitchMonitor(5).RSTPStatistics(18).RSTPStatisticsTable(1)

	--swhRSTPStatisticsTable OBJECT-TYPE
	--	SYNTAX    SEQUENCE OF SwhRSTPStatisticsEntry
	--	ACCESS    not-accessible
	--	STATUS    mandatory
	--	DESCRIPTION
	--		"Table of RSTP Statistics."
	--	::= { swhRSTPStatistics 1 }

	-- Table Entry
	--swhRSTPStatisticsEntry OBJECT-TYPE
	--	SYNTAX    SwhRSTPStatisticsEntry
	--	ACCESS    not-accessible
	--	STATUS    mandatory
	--	DESCRIPTION
	--		"An entry in the table, containing information
	--		about RSTP Statistics."
	--	INDEX    { swhRSTPStatisticsIndex }
	--	::= { swhRSTPStatisticsTable 1 }

	--SwhRSTPStatisticsEntry ::=
	--	SEQUENCE {
	--		swhRSTPStatisticsIndex
	--			INTEGER,
	--		swhRSTPStatisticsPort
	--			DisplayString,
	--		swhRSTPStatisticsRSTPTransmitted
	--			Counter,
	--		swhRSTPStatisticsSTPTransmitted
	--			Counter,
	--		swhRSTPStatisticsTCNTransmitted
	--			Counter,
	--		swhRSTPStatisticsRSTPReceived
	--			Counter,
	--		swhRSTPStatisticsSTPReceived
	--			Counter,
	--		swhRSTPStatisticsTCNReceived
	--			Counter,
	--		swhRSTPStatisticsIllegalReceived
	--			Counter,
	--		swhRSTPStatisticsUnknownReceived
	--			Counter
	--	}

	--swhRSTPStatisticsIndex OBJECT-TYPE
	--	SYNTAX    INTEGER (0..2147483647)
	--	ACCESS    not-accessible
	--	STATUS    mandatory
	--	DESCRIPTION
	--		"A unique value for each Port."
	--	::= { swhRSTPStatisticsEntry 1 }

	--swhRSTPStatisticsRSTPTransmitted OBJECT-TYPE
	--	SYNTAX    Counter
	--	ACCESS    read-only
	--	STATUS    mandatory
	--	DESCRIPTION
	--		""
	--	::= { swhRSTPStatisticsEntry 3 }

	--swhRSTPStatisticsSTPTransmitted OBJECT-TYPE
	--	SYNTAX    Counter
	--	ACCESS    read-only
	--	STATUS    mandatory
	--	DESCRIPTION
	--		""
	--	::= { swhRSTPStatisticsEntry 5 }

	--swhRSTPStatisticsTCNTransmitted OBJECT-TYPE
	--	SYNTAX    Counter
	--	ACCESS    read-only
	--	STATUS    mandatory
	--	DESCRIPTION
	--		""
	--	::= { swhRSTPStatisticsEntry 7 }

	--swhRSTPStatisticsRSTPReceived OBJECT-TYPE
	--	SYNTAX    Counter
	--	ACCESS    read-only
	--	STATUS    mandatory
	--	DESCRIPTION
	--		""
	--	::= { swhRSTPStatisticsEntry 9 }

	--swhRSTPStatisticsSTPReceived OBJECT-TYPE
	--	SYNTAX    Counter
	--	ACCESS    read-only
	--	STATUS    mandatory
	--	DESCRIPTION
	--		""
	--	::= { swhRSTPStatisticsEntry 11 }

	--swhRSTPStatisticsTCNReceived OBJECT-TYPE
	--	SYNTAX    Counter
	--	ACCESS    read-only
	--	STATUS    mandatory
	--	DESCRIPTION
	--		""
	--	::= { swhRSTPStatisticsEntry 13 }

	--swhRSTPStatisticsIllegalReceived OBJECT-TYPE
	--	SYNTAX    Counter
	--	ACCESS    read-only
	--	STATUS    mandatory
	--	DESCRIPTION
	--		""
	--	::= { swhRSTPStatisticsEntry 15 }

	--swhRSTPStatisticsUnknownReceived OBJECT-TYPE
	--	SYNTAX    Counter
	--	ACCESS    read-only
	--	STATUS    mandatory
	--	DESCRIPTION
	--		""
	--	::= { swhRSTPStatisticsEntry 17 }

	--swhRSTPStatisticsPort OBJECT-TYPE
	--	SYNTAX    DisplayString
	--	ACCESS    read-only
	--	STATUS    mandatory
	--	DESCRIPTION
	--		"Port Name"
	--	::= { swhRSTPStatisticsEntry 18 }


-- SwitchMonitor(5).LACPPortStatus(22)

--	swhLACPPortStatusTable OBJECT-TYPE
--		SYNTAX    SEQUENCE OF SwhLACPPortStatusEntry
--		ACCESS    not-accessible
--		STATUS    mandatory
--		DESCRIPTION
--			"Table of RSTP VLAN Bridge Overview."
--		::= { swhLACPPortStatus 1 }
--
	-- Table Entry
--	swhLACPPortStatusEntry OBJECT-TYPE
--		SYNTAX    SwhLACPPortStatusEntry
--		ACCESS    not-accessible
--		STATUS    mandatory
--		DESCRIPTION
--			"An entry in the table, containing information
--			about RSTP VLAN Bridge mode."
--		INDEX    { swhLACPPortStatusIndex }
--		::= { swhLACPPortStatusTable 1 }
--
--	SwhLACPPortStatusEntry ::=
--		SEQUENCE {
--			swhLACPPortStatusIndex
--				INTEGER,
--			swhLACPPortStatusLACPOperationalState
--				INTEGER,
--			swhLACPPortStatusKey
--				INTEGER,
--			swhLACPPortStatusAggrID
--				INTEGER,
--			swhLACPPortStatusPartnerID
--				DisplayString,
--			swhLACPPortStatusPartnerPort
--				INTEGER
--		}
--
--	swhLACPPortStatusIndex OBJECT-TYPE
--		SYNTAX    INTEGER (0..2147483647)
--		ACCESS    not-accessible
--		STATUS    mandatory
--		DESCRIPTION
--			"A unique value for each Port."
--		::= { swhLACPPortStatusEntry 1 }
--
--	swhLACPPortStatusPartnerID OBJECT-TYPE
--		SYNTAX    INTEGER
--		ACCESS    read-only
--		STATUS    mandatory
--		DESCRIPTION
--			"Partner ID"
--		::= { swhLACPPortStatusEntry 2 }
--
--	swhLACPPortStatusPartnerPort OBJECT-TYPE
--		SYNTAX    INTEGER
--		ACCESS    read-only
--		STATUS    mandatory
--		DESCRIPTION
--			"Partner Port"
--		::= { swhLACPPortStatusEntry 3 }
--
--	swhLACPPortStatusLACPOperationalState OBJECT-TYPE
--		SYNTAX    INTEGER { no(0), yes(1) }
--		ACCESS    read-only
--		STATUS    mandatory
--		DESCRIPTION
--			"LACP Operational State"
--		::= { swhLACPPortStatusEntry 4 }
--
--	swhLACPPortStatusKey OBJECT-TYPE
--		SYNTAX    INTEGER
--		ACCESS    read-only
--		STATUS    mandatory
--		DESCRIPTION
--			"Key"
--		::= { swhLACPPortStatusEntry 5 }
--
--	swhLACPPortStatusAggrID OBJECT-TYPE
--		SYNTAX    INTEGER
--		ACCESS    read-only
--		STATUS    mandatory
--		DESCRIPTION
--			"Key"
--		::= { swhLACPPortStatusEntry 6 }
--
--	swhLACPPortStatusPartnerID OBJECT-TYPE
--		SYNTAX    DisplayString
--		ACCESS    read-only
--		STATUS    mandatory
--		DESCRIPTION
--			"Partner ID"
--		::= { swhLACPPortStatusEntry 7 }
--
--
-- SwitchMonitor(5).LACPStatistics(24)
--
--	swhLACPStatisticsTable OBJECT-TYPE
--		SYNTAX    SEQUENCE OF SWHLACPStatisticsEntry
--		ACCESS    not-accessible
--		STATUS    mandatory
--		DESCRIPTION
--			"Table of RSTP Statistics."
--		::= { swhLACPStatistics 1 }
--
--	swhLACPStatisticsClearCountersOfAllPort OBJECT-TYPE
--		SYNTAX    INTEGER { normal(0), clear(1) }
--		ACCESS    read-write
--		STATUS    mandatory
--		DESCRIPTION
--			"Clear Counters of All Port"
--		::= { swhLACPStatistics 2  }
--
	-- Table Entry
--	swhLACPStatisticsEntry OBJECT-TYPE
--		SYNTAX    SWHLACPStatisticsEntry
--		ACCESS    not-accessible
--		STATUS    mandatory
--		DESCRIPTION
--			"An entry in the table, containing information
--			about RSTP Statistics."
--		INDEX    { swhLACPStatisticsIndex }
--		::= { swhLACPStatisticsTable 1 }
--
--	SWHLACPStatisticsEntry ::=
--		SEQUENCE {
--			swhLACPStatisticsIndex
--				INTEGER,
--			swhLACPStatisticsLACPTransmitted
--				Counter,
		--	swhLACPStatisticsMarkTransmitted
		--		Counter,
		--	swhLACPStatisticsRespTransmitted
		--		Counter,
--			swhLACPStatisticsLACPReceived
--				Counter,
		--	swhLACPStatisticsMarkReceived
		--		Counter,
		--	swhLACPStatisticsRespReceived
		--		Counter,
--			swhLACPStatisticsIllegalReceived
--				Counter,
--			swhLACPStatisticsUnknownReceived
--				Counter,
--			swhLACPStatisticsClear
--				INTEGER
--		}
--
--	swhLACPStatisticsIndex OBJECT-TYPE
--		SYNTAX    INTEGER (0..2147483647)
--		ACCESS    not-accessible
--		STATUS    mandatory
--		DESCRIPTION
--			"A unique value for each Port."
--		::= { swhLACPStatisticsEntry 1 }
--
--	swhLACPStatisticsLACPTransmitted OBJECT-TYPE
--		SYNTAX    Counter
--		ACCESS    read-only
--		STATUS    mandatory
--		DESCRIPTION
--			""
--		::= { swhLACPStatisticsEntry 3 }
--
--	swhLACPStatisticsMarkTransmitted OBJECT-TYPE
--		SYNTAX    Counter
--		ACCESS    read-only
--		STATUS    mandatory
--		DESCRIPTION
--			""
--		::= { swhLACPStatisticsEntry 5 }
--
--	swhLACPStatisticsRespTransmitted OBJECT-TYPE
--		SYNTAX    Counter
--		ACCESS    read-only
--		STATUS    mandatory
--		DESCRIPTION
--			""
--		::= { swhLACPStatisticsEntry 7 }
--
--	swhLACPStatisticsLACPReceived OBJECT-TYPE
--		SYNTAX    Counter
--		ACCESS    read-only
--		STATUS    mandatory
--		DESCRIPTION
--			""
--		::= { swhLACPStatisticsEntry 9 }
--
--	swhLACPStatisticsMarkReceived OBJECT-TYPE
--		SYNTAX    Counter
--		ACCESS    read-only
--		STATUS    mandatory
--		DESCRIPTION
--			""
--		::= { swhLACPStatisticsEntry 11 }
--
--	swhLACPStatisticsRespReceived OBJECT-TYPE
--		SYNTAX    Counter
--		ACCESS    read-only
--		STATUS    mandatory
--		DESCRIPTION
--			""
--		::= { swhLACPStatisticsEntry 13 }
--
--	swhLACPStatisticsIllegalReceived OBJECT-TYPE
--		SYNTAX    Counter
--		ACCESS    read-only
--		STATUS    mandatory
--		DESCRIPTION
--			""
--		::= { swhLACPStatisticsEntry 15 }
--
--	swhLACPStatisticsUnknownReceived OBJECT-TYPE
--		SYNTAX    Counter
--		ACCESS    read-only
--		STATUS    mandatory
--		DESCRIPTION
--			""
--		::= { swhLACPStatisticsEntry 17 }
--
--	swhLACPStatisticsClear OBJECT-TYPE
--		SYNTAX    INTEGER { normal(0), clear(1) }
--		ACCESS    read-write
--		STATUS    mandatory
--		DESCRIPTION
--			"Clear Counters of This module"
--		::= { swhLACPStatisticsEntry 19 }


-- SwitchMonitor(5).Layer2ProtocolTunnelStatus(25)

--	swhL2PTStatusClearCountersOfAllPort OBJECT-TYPE
--		SYNTAX    INTEGER { normal(0), clear(1) }
--		ACCESS    read-write
--		STATUS    mandatory
--		DESCRIPTION
--			"Clear all Layer 2 Protocol Tunnel Status."
--		::= { swhLayer2ProtocolTunnelStatus 2 }
--
--	swhL2PTStatusPortSelect OBJECT-TYPE
--		SYNTAX    INTEGER { port01(0),
--		                    port02(1),
--		                    port03(2),
--		                    port04(3),
--		                    port05(4),
--		                    port06(5)
--		                  }
--		ACCESS    read-write
--		STATUS    mandatory
--		DESCRIPTION
--			"Display L2PT Counters of the port which is selected."
--		::= { swhLayer2ProtocolTunnelStatus 3 }
--
--	swhL2PTStatusPortClear OBJECT-TYPE
--		SYNTAX    INTEGER { normal(0), clear(1) }
--		ACCESS    read-write
--		STATUS    mandatory
--		DESCRIPTION
--			"Clear this port counters."
--		::= { swhLayer2ProtocolTunnelStatus 4 }
--
--
-- SwitchMonitor(5).Layer2ProtocolTunnelStatus(25).L2PTStatusTable(5)
--
--	swhL2PTStatusTable OBJECT-TYPE
--		SYNTAX    SEQUENCE OF SwhL2PTStatusEntry
--		ACCESS    not-accessible
--		STATUS    mandatory
--		DESCRIPTION
--			"Table of L2PT Counters."
--		::= { swhLayer2ProtocolTunnelStatus 5 }
--
	-- Table Entry
--	swhL2PTStatusEntry OBJECT-TYPE
--		SYNTAX    SwhL2PTStatusEntry
--		ACCESS    not-accessible
--		STATUS    mandatory
--		DESCRIPTION
--			"An entry in the table, containing information
--			about L2PT Counters"
--		INDEX    { swhL2PTStatusIndex }
--		::= { swhL2PTStatusTable 1 }
--
--	SwhL2PTStatusEntry ::=
--		SEQUENCE {
--			swhL2PTStatusIndex
--				INTEGER,
--			swhL2PTStatusCounterName
--				DisplayString,
--			swhL2PTStatusState
--				INTEGER,
--			swhL2PTStatusEncapsulationCounters
--				Counter,
--			swhL2PTStatusDecapsulationCounters
--				Counter,
--			swhL2PTStatusDropCounters
--				Counter
--		}
--
--	swhL2PTStatusIndex OBJECT-TYPE
--		SYNTAX    INTEGER (0..2147483647)
--		ACCESS    not-accessible
--		STATUS    mandatory
--		DESCRIPTION
--			"A unique value for L2PT index."
--		::= { swhL2PTStatusEntry 1 }
--
--	swhL2PTStatusCounterName OBJECT-TYPE
--		SYNTAX    DisplayString
--		ACCESS    read-only
--		STATUS    mandatory
--		DESCRIPTION
--			"L2PT Counter Name."
--		::= { swhL2PTStatusEntry 2 }
--
--	swhL2PTStatusState OBJECT-TYPE
--		SYNTAX    INTEGER { disable(0), enable(1) }
--		ACCESS    read-only
--		STATUS    mandatory
--		DESCRIPTION
--			"State."
--		::= { swhL2PTStatusEntry 3 }
--
--	swhL2PTStatusEncapsulationCounters OBJECT-TYPE
--		SYNTAX    Counter
--		ACCESS    read-only
--		STATUS    mandatory
--		DESCRIPTION
--			"Encapsulation Counters."
--		::= { swhL2PTStatusEntry 4 }
--
--	swhL2PTStatusDecapsulationCounters OBJECT-TYPE
--		SYNTAX    Counter
--		ACCESS    read-only
--		STATUS    mandatory
--		DESCRIPTION
--			"Decapsulation Counters."
--		::= { swhL2PTStatusEntry 5 }
--
--	swhL2PTStatusDropCounters OBJECT-TYPE
--		SYNTAX    Counter
--		ACCESS    read-only
--		STATUS    mandatory
--		DESCRIPTION
--			"Drop Counters."
--		::= { swhL2PTStatusEntry 6 }


-- SwitchMonitor(5).IGMPStatus(26)

--	swhIGMPStatusUpdate OBJECT-TYPE
--		SYNTAX    INTEGER { normal(0), update(1) }
--		ACCESS    read-write
--		STATUS    mandatory
--		DESCRIPTION
--			"Update IGMP status table."
--		::= { swhIGMPStatus 3 }

--	swhIGMPStatusState OBJECT-TYPE
--		SYNTAX    DisplayString
--		ACCESS    read-only
--		STATUS    mandatory
--		DESCRIPTION
--			"The state of IGMP status table."
--		::= { swhIGMPStatus 5 }

	swhIGMPStatusTable OBJECT-TYPE
		SYNTAX    SEQUENCE OF SwhIGMPStatusEntry
		ACCESS    not-accessible
		STATUS    mandatory
		DESCRIPTION
			"Table of IGMP Statistics."
		::= { swhIGMPStatus 2 }

	-- Table Entry
	swhIGMPStatusEntry OBJECT-TYPE
		SYNTAX    SwhIGMPStatusEntry
		ACCESS    not-accessible
		STATUS    mandatory
		DESCRIPTION
			"An entry in the table, containing information
			about RSTP Statistics."
		INDEX    { swhIGMPStatusIndex }
		::= { swhIGMPStatusTable 1 }

	SwhIGMPStatusEntry ::=
		SEQUENCE {
			swhIGMPStatusIndex
				INTEGER,
			swhIGMPStatusVLANID
				INTEGER,
--			swhIGMPStatusIsMVRVLANID
--				INTEGER,
			swhIGMPStatusQuerier
				INTEGER,
			swhIGMPStatusQueriesTransmitted
				INTEGER,
			swhIGMPStatusQueriesReceived
				INTEGER,
			swhIGMPStatusV1Reports
				INTEGER,
			swhIGMPStatusV2Reports
				INTEGER,
			swhIGMPStatusV3Reports
				INTEGER,
			swhIGMPStatusV2Leaves
				INTEGER
		}

	swhIGMPStatusIndex OBJECT-TYPE
		SYNTAX    INTEGER (0..2147483647)
		ACCESS    not-accessible
		STATUS    mandatory
		DESCRIPTION
			"A unique value for each Port."
		::= { swhIGMPStatusEntry 1 }

	swhIGMPStatusVLANID OBJECT-TYPE
		SYNTAX    INTEGER
		ACCESS    read-only
		STATUS    mandatory
		DESCRIPTION
			""
		::= { swhIGMPStatusEntry 3 }

	swhIGMPStatusQuerier OBJECT-TYPE
		SYNTAX    INTEGER { idle(0), active(1) }
		ACCESS    read-only
		STATUS    mandatory
		DESCRIPTION
			""
		::= { swhIGMPStatusEntry 5 }

	swhIGMPStatusQueriesTransmitted OBJECT-TYPE
		SYNTAX    INTEGER
		ACCESS    read-only
		STATUS    mandatory
		DESCRIPTION
			""
		::= { swhIGMPStatusEntry 7 }

	swhIGMPStatusQueriesReceived OBJECT-TYPE
		SYNTAX    INTEGER
		ACCESS    read-only
		STATUS    mandatory
		DESCRIPTION
			""
		::= { swhIGMPStatusEntry 9 }

	swhIGMPStatusV1Reports OBJECT-TYPE
		SYNTAX    INTEGER
		ACCESS    read-only
		STATUS    mandatory
		DESCRIPTION
			""
		::= { swhIGMPStatusEntry 11 }

	swhIGMPStatusV2Reports OBJECT-TYPE
		SYNTAX    INTEGER
		ACCESS    read-only
		STATUS    mandatory
		DESCRIPTION
			""
		::= { swhIGMPStatusEntry 13 }

	swhIGMPStatusV3Reports OBJECT-TYPE
		SYNTAX    INTEGER
		ACCESS    read-only
		STATUS    mandatory
		DESCRIPTION
			""
		::= { swhIGMPStatusEntry 15 }

	swhIGMPStatusV2Leaves OBJECT-TYPE
		SYNTAX    INTEGER
		ACCESS    read-only
		STATUS    mandatory
		DESCRIPTION
			""
		::= { swhIGMPStatusEntry 17 }

--	swhIGMPStatusIsMVRVLANID OBJECT-TYPE
--		SYNTAX    INTEGER { b(0), v(1) }
--		ACCESS    read-only
--		STATUS    mandatory
--		DESCRIPTION
--			"Is it MVR VLAN ID? v: yes, b: no"
--		::= { swhIGMPStatusEntry 18 }


-- SwitchMonitor(5).MLDStatus(27)

--	swhMLDStatusUpdate OBJECT-TYPE
--		SYNTAX    INTEGER { normal(0), update(1) }
--		ACCESS    read-write
--		STATUS    mandatory
--		DESCRIPTION
--			"Update MLD status table."
--		::= { swhMLDStatus 3 }

--	swhMLDStatusState OBJECT-TYPE
--		SYNTAX    DisplayString
--		ACCESS    read-only
--		STATUS    mandatory
--		DESCRIPTION
--			"The state of MLD status table."
--		::= { swhMLDStatus 5 }

	swhMLDStatusTable OBJECT-TYPE
		SYNTAX    SEQUENCE OF SwhMLDStatusEntry
		ACCESS    not-accessible
		STATUS    mandatory
		DESCRIPTION
			"Table of MLD Statistics."
		::= { swhMLDStatus 2 }

	-- Table Entry
	swhMLDStatusEntry OBJECT-TYPE
		SYNTAX    SwhMLDStatusEntry
		ACCESS    not-accessible
		STATUS    mandatory
		DESCRIPTION
			"An entry in the table, containing information
			about RSTP Statistics."
		INDEX    { swhMLDStatusIndex }
		::= { swhMLDStatusTable 1 }

	SwhMLDStatusEntry ::=
		SEQUENCE {
			swhMLDStatusIndex
				INTEGER,
			swhMLDStatusVLANID
				INTEGER,
--			swhMLDStatusIsMVRVLANID
--				INTEGER,
			swhMLDStatusQuerier
				INTEGER,
			swhMLDStatusQueriesTransmitted
				INTEGER,
			swhMLDStatusQueriesReceived
				INTEGER,
			swhMLDStatusV1Reports
				INTEGER,
			swhMLDStatusV2Reports
				INTEGER,
			swhMLDStatusDone
				INTEGER
		}

	swhMLDStatusIndex OBJECT-TYPE
		SYNTAX    INTEGER (0..2147483647)
		ACCESS    not-accessible
		STATUS    mandatory
		DESCRIPTION
			"A unique value for each Port."
		::= { swhMLDStatusEntry 1 }

	swhMLDStatusVLANID OBJECT-TYPE
		SYNTAX    INTEGER
		ACCESS    read-only
		STATUS    mandatory
		DESCRIPTION
			""
		::= { swhMLDStatusEntry 3 }

	swhMLDStatusQuerier OBJECT-TYPE
		SYNTAX    INTEGER { idle(0), active(1) }
		ACCESS    read-only
		STATUS    mandatory
		DESCRIPTION
			""
		::= { swhMLDStatusEntry 5 }

	swhMLDStatusQueriesTransmitted OBJECT-TYPE
		SYNTAX    INTEGER
		ACCESS    read-only
		STATUS    mandatory
		DESCRIPTION
			""
		::= { swhMLDStatusEntry 7 }

	swhMLDStatusQueriesReceived OBJECT-TYPE
		SYNTAX    INTEGER
		ACCESS    read-only
		STATUS    mandatory
		DESCRIPTION
			""
		::= { swhMLDStatusEntry 9 }

	swhMLDStatusV1Reports OBJECT-TYPE
		SYNTAX    INTEGER
		ACCESS    read-only
		STATUS    mandatory
		DESCRIPTION
			""
		::= { swhMLDStatusEntry 11 }

	swhMLDStatusV2Reports OBJECT-TYPE
		SYNTAX    INTEGER
		ACCESS    read-only
		STATUS    mandatory
		DESCRIPTION
			""
		::= { swhMLDStatusEntry 13 }

	swhMLDStatusDone OBJECT-TYPE
		SYNTAX    INTEGER
		ACCESS    read-only
		STATUS    mandatory
		DESCRIPTION
			""
		::= { swhMLDStatusEntry 15 }

--	swhMLDStatusIsMVRVLANID OBJECT-TYPE
--		SYNTAX    INTEGER { b(0), v(1) }
--		ACCESS    read-only
--		STATUS    mandatory
--		DESCRIPTION
--			"Is it MVR VLAN ID? v: yes, b: no"
--		::= { swhMLDStatusEntry 16 }


-- SwitchMonitor(5).IGMPGroupTable(28)

	swhIGMPState OBJECT-TYPE
		SYNTAX    INTEGER { disable(0), enable(1) }
		ACCESS    read-only
		STATUS    mandatory
		DESCRIPTION
			"IGMP Snooping is disable or enable."
		::= { swhIGMPGroupTable 1 }

--	swhIGMPTableUpdate OBJECT-TYPE
--		SYNTAX    INTEGER { normal(0), update(1) }
--		ACCESS    read-write
--		STATUS    mandatory
--		DESCRIPTION
--			"Update IGMP Snooping Group Table."
--		::= { swhIGMPGroupTable 3 }


-- SwitchMonitor(5).IGMPGroupTable(28).IGMPTable(2)

	swhIGMPTable OBJECT-TYPE
		SYNTAX    SEQUENCE OF SwhIGMPTableEntry
		ACCESS    not-accessible
		STATUS    mandatory
		DESCRIPTION
			"Table of IGMP Group."
		::= { swhIGMPGroupTable 2 }

 	-- Table Entry
	swhIGMPTableEntry OBJECT-TYPE
		SYNTAX    SwhIGMPTableEntry
		ACCESS    not-accessible
		STATUS    mandatory
		DESCRIPTION
			"An entry in the table, containing information
			 about multicast groups, port members, queries, reports, time of aging out."
		INDEX    { swhIGMPGroupTableIndex }
		::= { swhIGMPTable 1 }

	SwhIGMPTableEntry ::=
		SEQUENCE {
			swhIGMPGroupTableIndex
				INTEGER,
			swhIGMPGroupTableVID
				INTEGER,
--			swhIGMPGroupTableIsMVRVID
--				INTEGER,
			swhIGMPGroupTableGroup
				DisplayString,
			swhIGMPGroupTablePort1
				INTEGER,
			swhIGMPGroupTablePort2
				INTEGER,
			swhIGMPGroupTablePort3
				INTEGER,
			swhIGMPGroupTablePort4
				INTEGER,
			swhIGMPGroupTablePort5
				INTEGER,
			swhIGMPGroupTablePort6
				INTEGER
		}

	swhIGMPGroupTableIndex OBJECT-TYPE
		SYNTAX    INTEGER (0..2147483647)
		ACCESS    not-accessible
		STATUS    mandatory
		DESCRIPTION
			"A unique value multicast groups index."
		::= { swhIGMPTableEntry 1 }

	swhIGMPGroupTableGroup OBJECT-TYPE
		SYNTAX    DisplayString (SIZE (0..255))
		ACCESS    read-only
		STATUS    mandatory
		DESCRIPTION
			"Group."
		::= { swhIGMPTableEntry 3 }

	swhIGMPGroupTablePort1 OBJECT-TYPE
		SYNTAX    INTEGER { b(0), v(1) }
		ACCESS    read-only
		STATUS    mandatory
		DESCRIPTION
			"b:Blocked  v:Member"
		::= { swhIGMPTableEntry 5 }

	swhIGMPGroupTablePort2 OBJECT-TYPE
		SYNTAX    INTEGER { b(0), v(1) }
		ACCESS    read-only
		STATUS    mandatory
		DESCRIPTION
			"b:Blocked  v:Member"
		::= { swhIGMPTableEntry 6 }

	swhIGMPGroupTablePort3 OBJECT-TYPE
		SYNTAX    INTEGER { b(0), v(1) }
		ACCESS    read-only
		STATUS    mandatory
		DESCRIPTION
			"b:Blocked  v:Member"
		::= { swhIGMPTableEntry 7 }

	swhIGMPGroupTablePort4 OBJECT-TYPE
		SYNTAX    INTEGER { b(0), v(1) }
		ACCESS    read-only
		STATUS    mandatory
		DESCRIPTION
			"b:Blocked  v:Member"
		::= { swhIGMPTableEntry 8 }

	swhIGMPGroupTablePort5 OBJECT-TYPE
		SYNTAX    INTEGER { b(0), v(1) }
		ACCESS    read-only
		STATUS    mandatory
		DESCRIPTION
			"b:Blocked  v:Member"
		::= { swhIGMPTableEntry 9 }

	swhIGMPGroupTablePort6 OBJECT-TYPE
		SYNTAX    INTEGER { b(0), v(1) }
		ACCESS    read-only
		STATUS    mandatory
		DESCRIPTION
			"b:Blocked  v:Member"
		::= { swhIGMPTableEntry 10 }


--	swhIGMPGroupTableIsMVRVID OBJECT-TYPE
--		SYNTAX    INTEGER { b(0), v(1) }
--		ACCESS    read-only
--		STATUS    mandatory
--		DESCRIPTION
--			"Is it MVR VLAN ID? v: yes, b: no"
--		::= { swhIGMPTableEntry 53 }

	swhIGMPGroupTableVID OBJECT-TYPE
		SYNTAX    INTEGER
		ACCESS    read-only
		STATUS    mandatory
		DESCRIPTION
			"VLAN ID."
		::= { swhIGMPTableEntry 60 }


-- SwitchMonitor(5).MLDGroupTable(29)

	swhMLDState OBJECT-TYPE
		SYNTAX    INTEGER { disable(0), enable(1) }
		ACCESS    read-only
		STATUS    mandatory
		DESCRIPTION
			"MLD Snooping is disable or enable."
		::= { swhMLDGroupTable 1 }

--	swhMLDTableUpdate OBJECT-TYPE
--		SYNTAX    INTEGER { normal(0), update(1) }
--		ACCESS    read-write
--		STATUS    mandatory
--		DESCRIPTION
--			"Update MLD Snooping Group Table."
--		::= { swhMLDGroupTable 3 }


-- SwitchMonitor(5).MLDGroupTable(29).MLDTable(2)

	swhMLDTable OBJECT-TYPE
		SYNTAX    SEQUENCE OF SwhMLDTableEntry
		ACCESS    not-accessible
		STATUS    mandatory
		DESCRIPTION
			"Table of MLD Group."
		::= { swhMLDGroupTable 2 }

 	-- Table Entry
	swhMLDTableEntry OBJECT-TYPE
		SYNTAX    SwhMLDTableEntry
		ACCESS    not-accessible
		STATUS    mandatory
		DESCRIPTION
			"An entry in the table, containing information
			 about multicast groups, port members, queries, reports, time of aging out."
		INDEX    { swhMLDGroupTableIndex }
		::= { swhMLDTable 1 }

	SwhMLDTableEntry ::=
		SEQUENCE {
			swhMLDGroupTableIndex
				INTEGER,
			swhMLDGroupTableVID
				INTEGER,
--			swhMLDGroupTableIsMVRVID
--				INTEGER,
			swhMLDGroupTableGroup
				DisplayString,
			swhMLDGroupTablePort1
				INTEGER,
			swhMLDGroupTablePort2
				INTEGER,
			swhMLDGroupTablePort3
				INTEGER,
			swhMLDGroupTablePort4
				INTEGER,
			swhMLDGroupTablePort5
				INTEGER,
			swhMLDGroupTablePort6
				INTEGER
		}

	swhMLDGroupTableIndex OBJECT-TYPE
		SYNTAX    INTEGER (0..2147483647)
		ACCESS    not-accessible
		STATUS    mandatory
		DESCRIPTION
			"A unique value multicast groups index."
		::= { swhMLDTableEntry 1 }

	swhMLDGroupTableGroup OBJECT-TYPE
		SYNTAX    DisplayString (SIZE (0..255))
		ACCESS    read-only
		STATUS    mandatory
		DESCRIPTION
			"Group."
		::= { swhMLDTableEntry 3 }

	swhMLDGroupTablePort1 OBJECT-TYPE
		SYNTAX    INTEGER { b(0), v(1) }
		ACCESS    read-only
		STATUS    mandatory
		DESCRIPTION
			"b:Blocked  v:Member"
		::= { swhMLDTableEntry 5 }

	swhMLDGroupTablePort2 OBJECT-TYPE
		SYNTAX    INTEGER { b(0), v(1) }
		ACCESS    read-only
		STATUS    mandatory
		DESCRIPTION
			"b:Blocked  v:Member"
		::= { swhMLDTableEntry 6 }

	swhMLDGroupTablePort3 OBJECT-TYPE
		SYNTAX    INTEGER { b(0), v(1) }
		ACCESS    read-only
		STATUS    mandatory
		DESCRIPTION
			"b:Blocked  v:Member"
		::= { swhMLDTableEntry 7 }

	swhMLDGroupTablePort4 OBJECT-TYPE
		SYNTAX    INTEGER { b(0), v(1) }
		ACCESS    read-only
		STATUS    mandatory
		DESCRIPTION
			"b:Blocked  v:Member"
		::= { swhMLDTableEntry 8 }

	swhMLDGroupTablePort5 OBJECT-TYPE
		SYNTAX    INTEGER { b(0), v(1) }
		ACCESS    read-only
		STATUS    mandatory
		DESCRIPTION
			"b:Blocked  v:Member"
		::= { swhMLDTableEntry 9 }

	swhMLDGroupTablePort6 OBJECT-TYPE
		SYNTAX    INTEGER { b(0), v(1) }
		ACCESS    read-only
		STATUS    mandatory
		DESCRIPTION
			"b:Blocked  v:Member"
		::= { swhMLDTableEntry 10 }


--	swhMLDGroupTableIsMVRVID OBJECT-TYPE
--		SYNTAX    INTEGER { b(0), v(1) }
--		ACCESS    read-only
--		STATUS    mandatory
--		DESCRIPTION
--			"Is it MVR VLAN ID? v: yes, b: no"
--		::= { swhMLDTableEntry 53 }

	swhMLDGroupTableVID OBJECT-TYPE
		SYNTAX    INTEGER
		ACCESS    read-only
		STATUS    mandatory
		DESCRIPTION
			"VLAN ID."
		::= { swhMLDTableEntry 60 }


-- SwitchMonitor(5).8021XPortStatus(32)

	swh8021XPortStatusTable OBJECT-TYPE
		SYNTAX    SEQUENCE OF Swh8021XPortStatusEntry
		ACCESS    not-accessible
		STATUS    mandatory
		DESCRIPTION
			"Table of 802.1X Port Status."
		::= { swh8021XPortStatus 1 }

	-- Table Entry
	swh8021XPortStatusEntry OBJECT-TYPE
		SYNTAX    Swh8021XPortStatusEntry
		ACCESS    not-accessible
		STATUS    mandatory
		DESCRIPTION
			"An entry in the table, containing information
			about 802.1X Port Status"
		INDEX    { swh8021XPortStatusIndex }
		::= { swh8021XPortStatusTable 1 }

	Swh8021XPortStatusEntry ::=
		SEQUENCE {
			swh8021XPortStatusIndex
				INTEGER,
			swh8021XPortStatusState
				INTEGER,
			swh8021XPortStatusLastSource
				DisplayString,
			swh8021XPortStatusLastID
				DisplayString,
			swh8021XPortStatusAssignedVLAN
				DisplayString,
			swh8021XPortStatusFallBackVLAN
				DisplayString
		}

	swh8021XPortStatusIndex OBJECT-TYPE
		SYNTAX    INTEGER (0..2147483647)
		ACCESS    not-accessible
		STATUS    mandatory
		DESCRIPTION
			"A unique value for vlan id index."
		::= { swh8021XPortStatusEntry 1 }

	swh8021XPortStatusState OBJECT-TYPE
		SYNTAX    INTEGER { linkdown(0), authorized(1), unauthorized(2), disabled(3) }
		ACCESS    read-only
		STATUS    mandatory
		DESCRIPTION
			"VLAN ID"
		::= { swh8021XPortStatusEntry 3 }

	swh8021XPortStatusLastSource OBJECT-TYPE
		SYNTAX    DisplayString
		ACCESS    read-only
		STATUS    mandatory
		DESCRIPTION
			"Multicast Group learned."
		::= { swh8021XPortStatusEntry 5 }

	swh8021XPortStatusLastID OBJECT-TYPE
		SYNTAX    DisplayString
		ACCESS    read-only
		STATUS    mandatory
		DESCRIPTION
			"Port Number"
		::= { swh8021XPortStatusEntry 7 }

	swh8021XPortStatusAssignedVLAN OBJECT-TYPE
		SYNTAX    DisplayString
		ACCESS    read-only
		STATUS    mandatory
		DESCRIPTION
			"VID"
		::= { swh8021XPortStatusEntry 9 }

	swh8021XPortStatusFallBackVLAN OBJECT-TYPE
		SYNTAX    DisplayString
		ACCESS    read-only
		STATUS    mandatory
		DESCRIPTION
			"FallBack VLAN"
		::= { swh8021XPortStatusEntry 10 }


-- SwitchMonitor(5).8021XStatistics(33)

	swh8021XStatisticsTable OBJECT-TYPE
		SYNTAX    SEQUENCE OF Swh8021XStatisticsEntry
		ACCESS    not-accessible
		STATUS    mandatory
		DESCRIPTION
			"Table of 802.1X Statistics."
		::= { swh8021XStatistics 1 }

	swh8021XStatisticsClearCountersOfAllPort OBJECT-TYPE
		SYNTAX    INTEGER { normal(0), clear(1) }
		ACCESS    read-write
		STATUS    mandatory
		DESCRIPTION
			"Clear Counters of All Port"
		::= { swh8021XStatistics 2 }

	-- Table Entry
	swh8021XStatisticsEntry OBJECT-TYPE
		SYNTAX    Swh8021XStatisticsEntry
		ACCESS    not-accessible
		STATUS    mandatory
		DESCRIPTION
			"An entry in the table, containing information
			about 802.1X Statistics"
		INDEX    { swh8021XStatisticsIndex }
		::= { swh8021XStatisticsTable 1 }

	Swh8021XStatisticsEntry ::=
		SEQUENCE {
			swh8021XStatisticsIndex
				INTEGER,
			swh8021XStatisticsRxTotal
				Counter,
			swh8021XStatisticsRxResponseID
				Counter,
			swh8021XStatisticsRxResponse
				Counter,
			swh8021XStatisticsRxStart
				Counter,
			swh8021XStatisticsRxLogoff
				Counter,
			swh8021XStatisticsRxInvalidType
				Counter,
			swh8021XStatisticsRxInvalidLength
				Counter,
			swh8021XStatisticsRxAccessChallenges
				Counter,
			swh8021XStatisticsRxOtherRequests
				Counter,
			swh8021XStatisticsRxAuthSuccesses
				Counter,
			swh8021XStatisticsRxAuthFailures
				Counter,
			swh8021XStatisticsTxTotal
				Counter,
			swh8021XStatisticsTxRequestID
				Counter,
			swh8021XStatisticsTxRequest
				Counter,
			swh8021XStatisticsTxResponses
				Counter,
			swh8021XStatisticsClear
				INTEGER
		}

	swh8021XStatisticsIndex OBJECT-TYPE
		SYNTAX    INTEGER (0..2147483647)
		ACCESS    not-accessible
		STATUS    mandatory
		DESCRIPTION
			"A unique value for vlan id index."
		::= { swh8021XStatisticsEntry 1 }

	swh8021XStatisticsRxTotal OBJECT-TYPE
		SYNTAX    Counter
		ACCESS    read-only
		STATUS    mandatory
		DESCRIPTION
			"Rx Total"
		::= { swh8021XStatisticsEntry 2 }

	swh8021XStatisticsRxResponseID OBJECT-TYPE
		SYNTAX    Counter
		ACCESS    read-only
		STATUS    mandatory
		DESCRIPTION
			"Rx Response ID"
		::= { swh8021XStatisticsEntry 3 }

	swh8021XStatisticsRxResponse OBJECT-TYPE
		SYNTAX    Counter
		ACCESS    read-only
		STATUS    mandatory
		DESCRIPTION
			"Rx Response"
		::= { swh8021XStatisticsEntry 4 }

	swh8021XStatisticsRxStart OBJECT-TYPE
		SYNTAX    Counter
		ACCESS    read-only
		STATUS    mandatory
		DESCRIPTION
			"Rx Response"
		::= { swh8021XStatisticsEntry 5 }

	swh8021XStatisticsRxLogoff OBJECT-TYPE
		SYNTAX    Counter
		ACCESS    read-only
		STATUS    mandatory
		DESCRIPTION
			"Rx Response"
		::= { swh8021XStatisticsEntry 6 }

	swh8021XStatisticsRxInvalidType OBJECT-TYPE
		SYNTAX    Counter
		ACCESS    read-only
		STATUS    mandatory
		DESCRIPTION
			"Rx Response"
		::= { swh8021XStatisticsEntry 7 }

	swh8021XStatisticsRxInvalidLength OBJECT-TYPE
		SYNTAX    Counter
		ACCESS    read-only
		STATUS    mandatory
		DESCRIPTION
			"Rx Response"
		::= { swh8021XStatisticsEntry 8 }

	swh8021XStatisticsRxAccessChallenges OBJECT-TYPE
		SYNTAX    Counter
		ACCESS    read-only
		STATUS    mandatory
		DESCRIPTION
			"Rx Response"
		::= { swh8021XStatisticsEntry 9 }

	swh8021XStatisticsRxOtherRequests OBJECT-TYPE
		SYNTAX    Counter
		ACCESS    read-only
		STATUS    mandatory
		DESCRIPTION
			"Rx Response"
		::= { swh8021XStatisticsEntry 10 }

	swh8021XStatisticsRxAuthSuccesses OBJECT-TYPE
		SYNTAX    Counter
		ACCESS    read-only
		STATUS    mandatory
		DESCRIPTION
			"Rx Response"
		::= { swh8021XStatisticsEntry 11 }

	swh8021XStatisticsRxAuthFailures OBJECT-TYPE
		SYNTAX    Counter
		ACCESS    read-only
		STATUS    mandatory
		DESCRIPTION
			"Rx Response"
		::= { swh8021XStatisticsEntry 12 }

	swh8021XStatisticsTxTotal OBJECT-TYPE
		SYNTAX    Counter
		ACCESS    read-only
		STATUS    mandatory
		DESCRIPTION
			"Rx Response"
		::= { swh8021XStatisticsEntry 13 }

	swh8021XStatisticsTxRequestID OBJECT-TYPE
		SYNTAX    Counter
		ACCESS    read-only
		STATUS    mandatory
		DESCRIPTION
			"Rx Response"
		::= { swh8021XStatisticsEntry 14 }

	swh8021XStatisticsTxRequest OBJECT-TYPE
		SYNTAX    Counter
		ACCESS    read-only
		STATUS    mandatory
		DESCRIPTION
			"Rx Response"
		::= { swh8021XStatisticsEntry 15 }

	swh8021XStatisticsTxResponses OBJECT-TYPE
		SYNTAX    Counter
		ACCESS    read-only
		STATUS    mandatory
		DESCRIPTION
			"Rx Response"
		::= { swh8021XStatisticsEntry 16 }

	swh8021XStatisticsClear OBJECT-TYPE
		SYNTAX    INTEGER { normal(0), clear(1) }
		ACCESS    read-write
		STATUS    mandatory
		DESCRIPTION
			"Clear Counters of This module"
		::= { swh8021XStatisticsEntry 17  }


-- SwitchMonitor(5).SFPInformation(34)

	swhSFPPortInfo
		OBJECT IDENTIFIER ::= { swhSFPInformation 1 }
	swhSFPPortState
		OBJECT IDENTIFIER ::= { swhSFPInformation 2 }


-- SwitchMonitor(5).SFPInformation(34).SFPPortInfo(1).SFPPortInfoTable(1)

	swhSFPPortInfoTable OBJECT-TYPE
		SYNTAX    SEQUENCE OF SwhSFPPortInfoEntry
		ACCESS    not-accessible
		STATUS    mandatory
		DESCRIPTION
			"Table of SFP Port Info."
		::= { swhSFPPortInfo 1 }

	-- Table Entry
	swhSFPPortInfoEntry OBJECT-TYPE
		SYNTAX    SwhSFPPortInfoEntry
		ACCESS    not-accessible
		STATUS    mandatory
		DESCRIPTION
			"An entry in the table, containing information
			about SFP Port Info."
		INDEX    { swhSFPPortInfoIndex }
		::= { swhSFPPortInfoTable 1 }

	SwhSFPPortInfoEntry ::=
		SEQUENCE {
			swhSFPPortInfoIndex
				INTEGER,
			swhSFPPortInfoPortName
				DisplayString,
			swhSFPPortInfoSpeed
				DisplayString,
			swhSFPPortInfoDistance
				DisplayString,
			swhSFPPortInfoVendorName
				DisplayString,
			swhSFPPortInfoVendorPN
				DisplayString,
			swhSFPPortInfoVendorSN
				DisplayString
		}

	swhSFPPortInfoIndex OBJECT-TYPE
		SYNTAX    INTEGER (0..2147483647)
		ACCESS    not-accessible
		STATUS    mandatory
		DESCRIPTION
			"A unique value for each port."
		::= { swhSFPPortInfoEntry 1 }

	swhSFPPortInfoPortName OBJECT-TYPE
		SYNTAX    DisplayString
		ACCESS    read-only
		STATUS    mandatory
		DESCRIPTION
			"Port Name"
		::= { swhSFPPortInfoEntry 3 }

	swhSFPPortInfoSpeed OBJECT-TYPE
		SYNTAX    DisplayString
		ACCESS    read-only
		STATUS    mandatory
		DESCRIPTION
			"Speed"
		::= { swhSFPPortInfoEntry 5 }

	swhSFPPortInfoDistance OBJECT-TYPE
		SYNTAX    DisplayString
		ACCESS    read-only
		STATUS    mandatory
		DESCRIPTION
			"Distance"
		::= { swhSFPPortInfoEntry 7 }

	swhSFPPortInfoVendorName OBJECT-TYPE
		SYNTAX    DisplayString
		ACCESS    read-only
		STATUS    mandatory
		DESCRIPTION
			"Vendor Name"
		::= { swhSFPPortInfoEntry 9 }

	swhSFPPortInfoVendorPN OBJECT-TYPE
		SYNTAX    DisplayString
		ACCESS    read-only
		STATUS    mandatory
		DESCRIPTION
			"Vendor PN"
		::= { swhSFPPortInfoEntry 11 }

	swhSFPPortInfoVendorSN OBJECT-TYPE
		SYNTAX    DisplayString
		ACCESS    read-only
		STATUS    mandatory
		DESCRIPTION
			"Vendor SN"
		::= { swhSFPPortInfoEntry 13 }


-- SwitchMonitor(5).SFPInformation(34).SFPPortState(2).SFPPortStateTable(1)

	swhSFPPortStateTable OBJECT-TYPE
		SYNTAX    SEQUENCE OF SwhSFPPortStateEntry
		ACCESS    not-accessible
		STATUS    mandatory
		DESCRIPTION
			"Table of SFP Port State."
		::= { swhSFPPortState 1 }

	-- Table Entry
	swhSFPPortStateEntry OBJECT-TYPE
		SYNTAX    SwhSFPPortStateEntry
		ACCESS    not-accessible
		STATUS    mandatory
		DESCRIPTION
			"An entry in the table, containing information
			about SFP Port State."
		INDEX    { swhSFPPortStateIndex }
		::= { swhSFPPortStateTable 1 }

	SwhSFPPortStateEntry ::=
		SEQUENCE {
			swhSFPPortStateIndex
				INTEGER,
			swhSFPPortStatePortName
				DisplayString,
			swhSFPPortStateTemperature
				DisplayString,
			swhSFPPortStateVoltage
				DisplayString,
			swhSFPPortStateTXBias
				DisplayString,
			swhSFPPortStateTXPower
				DisplayString,
			swhSFPPortStateRXPower
				DisplayString
		}

	swhSFPPortStateIndex OBJECT-TYPE
		SYNTAX    INTEGER (0..2147483647)
		ACCESS    not-accessible
		STATUS    mandatory
		DESCRIPTION
			"A unique value for each port."
		::= { swhSFPPortStateEntry 1 }

	swhSFPPortStatePortName OBJECT-TYPE
		SYNTAX    DisplayString
		ACCESS    read-only
		STATUS    mandatory
		DESCRIPTION
			"Port Name"
		::= { swhSFPPortStateEntry 3 }

	swhSFPPortStateTemperature OBJECT-TYPE
		SYNTAX    DisplayString
		ACCESS    read-only
		STATUS    mandatory
		DESCRIPTION
			"Port Temperature (C)"
		::= { swhSFPPortStateEntry 5 }

	swhSFPPortStateVoltage OBJECT-TYPE
		SYNTAX    DisplayString
		ACCESS    read-only
		STATUS    mandatory
		DESCRIPTION
			"Port Voltage (V)"
		::= { swhSFPPortStateEntry 7 }

	swhSFPPortStateTXBias OBJECT-TYPE
		SYNTAX    DisplayString
		ACCESS    read-only
		STATUS    mandatory
		DESCRIPTION
			"Port TX Bias (mA)"
		::= { swhSFPPortStateEntry 9 }

	swhSFPPortStateTXPower OBJECT-TYPE
		SYNTAX    DisplayString
		ACCESS    read-only
		STATUS    mandatory
		DESCRIPTION
			"Port TX Power (dBm)"
		::= { swhSFPPortStateEntry 11 }

	swhSFPPortStateRXPower OBJECT-TYPE
		SYNTAX    DisplayString
		ACCESS    read-only
		STATUS    mandatory
		DESCRIPTION
			"Port RX Power (dBm)"
		::= { swhSFPPortStateEntry 13 }


-- SwitchMonitor(5).DHCPSnoopingTable(35)


-- SwitchMonitor(5).DHCPSnoopingTable(35).DHCPSnoopingTableTable(7)

	swhDHCPSnoopingTableTable OBJECT-TYPE
		SYNTAX    SEQUENCE OF SwhDHCPSnoopingTableEntry
		ACCESS    not-accessible
		STATUS    mandatory
		DESCRIPTION
			"Table of DHCP Snooping Table."
		::= { swhDHCPSnoopingTable 7 }

	-- Table Entry
	swhDHCPSnoopingTableEntry OBJECT-TYPE
		SYNTAX    SwhDHCPSnoopingTableEntry
		ACCESS    not-accessible
		STATUS    mandatory
		DESCRIPTION
			"An entry in the table, containing information
			about RSTP VLAN Bridge mode."
		INDEX    { swhDHCPSnoopingTableIndex }
		::= { swhDHCPSnoopingTableTable 1 }

	SwhDHCPSnoopingTableEntry ::=
		SEQUENCE {
			swhDHCPSnoopingTableIndex
				INTEGER,
			swhDHCPSnoopingTableCliPort
				INTEGER,
			swhDHCPSnoopingTableSrvPort
				INTEGER,
			swhDHCPSnoopingTableVID
				INTEGER,
			swhDHCPSnoopingTableCliIPAddr
				IpAddress,
			swhDHCPSnoopingTableCliMacAddr
				MacAddress,
			swhDHCPSnoopingTableSrvIPAddr
				IpAddress,
			swhDHCPSnoopingTableTimeLeft
				DisplayString
--			swhDHCPSnoopingTableIPSourceGuardUnlimited
--				DisplayString
		}

	swhDHCPSnoopingTableIndex OBJECT-TYPE
		SYNTAX    INTEGER (0..2147483647)
		ACCESS    not-accessible
		STATUS    mandatory
		DESCRIPTION
			"A unique value for each Port."
		::= { swhDHCPSnoopingTableEntry 1 }

	swhDHCPSnoopingTableCliPort OBJECT-TYPE
		SYNTAX    INTEGER
		ACCESS    read-only
		STATUS    mandatory
		DESCRIPTION
			"Client Port Number"
		::= { swhDHCPSnoopingTableEntry 2 }

	swhDHCPSnoopingTableSrvPort OBJECT-TYPE
		SYNTAX    INTEGER
		ACCESS    read-only
		STATUS    mandatory
		DESCRIPTION
			"Server Port Number"
		::= { swhDHCPSnoopingTableEntry 3 }

	swhDHCPSnoopingTableVID OBJECT-TYPE
		SYNTAX    INTEGER
		ACCESS    read-only
		STATUS    mandatory
		DESCRIPTION
			"VLAN ID"
		::= { swhDHCPSnoopingTableEntry 4 }

	swhDHCPSnoopingTableCliIPAddr OBJECT-TYPE
		SYNTAX    IpAddress
		ACCESS    read-only
		STATUS    mandatory
		DESCRIPTION
			"IP Address"
		::= { swhDHCPSnoopingTableEntry 5 }

	swhDHCPSnoopingTableCliMacAddr OBJECT-TYPE
		SYNTAX    MacAddress
		ACCESS    read-only
		STATUS    mandatory
		DESCRIPTION
			"Client Mac Address"
		::= { swhDHCPSnoopingTableEntry 6 }

	swhDHCPSnoopingTableSrvIPAddr OBJECT-TYPE
		SYNTAX    IpAddress
		ACCESS    read-only
		STATUS    mandatory
		DESCRIPTION
			"IP Address"
		::= { swhDHCPSnoopingTableEntry 7 }

	swhDHCPSnoopingTableTimeLeft OBJECT-TYPE
		SYNTAX    DisplayString
		ACCESS    read-only
		STATUS    mandatory
		DESCRIPTION
			"UpTime"
		::= { swhDHCPSnoopingTableEntry 8 }

--	swhDHCPSnoopingTableIPSourceGuardUnlimited OBJECT-TYPE
--		SYNTAX    DisplayString
--		ACCESS    read-only
--		STATUS    mandatory
--		DESCRIPTION
--			"IP Source Guard Unlimited"
--		::= { swhDHCPSnoopingTableEntry 9 }


-- SwitchMonitor(5).DHCPSnoopingTable(35).DHCPv6SnoopingTableTable(8)

	swhDHCPv6SnoopingTableTable OBJECT-TYPE
		SYNTAX    SEQUENCE OF SwhDHCPv6SnoopingTableEntry
		ACCESS    not-accessible
		STATUS    mandatory
		DESCRIPTION
			"Table of DHCPv6 Snooping Table."
		::= { swhDHCPSnoopingTable 8 }

	-- Table Entry
	swhDHCPv6SnoopingTableEntry OBJECT-TYPE
		SYNTAX    SwhDHCPv6SnoopingTableEntry
		ACCESS    not-accessible
		STATUS    mandatory
		DESCRIPTION
			"An entry in the table, containing information
			about RSTP VLAN Bridge mode."
		INDEX    { swhDHCPv6SnoopingTableIndex }
		::= { swhDHCPv6SnoopingTableTable 1 }

	SwhDHCPv6SnoopingTableEntry ::=
		SEQUENCE {
			swhDHCPv6SnoopingTableIndex
				INTEGER,
			swhDHCPv6SnoopingTableCliPort
				INTEGER,
			swhDHCPv6SnoopingTableSrvPort
				INTEGER,
			swhDHCPv6SnoopingTableVID
				INTEGER,
			swhDHCPv6SnoopingTableCliIPAddr
				DisplayString,
			swhDHCPv6SnoopingTableCliMacAddr
				MacAddress,
			swhDHCPv6SnoopingTableSrvIPAddr
				DisplayString,
			swhDHCPv6SnoopingTableTimeLeft
				DisplayString
--			swhDHCPv6SnoopingTableIPSourceGuardUnlimited
--				DisplayString
		}

	swhDHCPv6SnoopingTableIndex OBJECT-TYPE
		SYNTAX    INTEGER (0..2147483647)
		ACCESS    not-accessible
		STATUS    mandatory
		DESCRIPTION
			"A unique value for each Port."
		::= { swhDHCPv6SnoopingTableEntry 1 }

	swhDHCPv6SnoopingTableCliPort OBJECT-TYPE
		SYNTAX    INTEGER
		ACCESS    read-only
		STATUS    mandatory
		DESCRIPTION
			"Client Port Number"
		::= { swhDHCPv6SnoopingTableEntry 2 }

	swhDHCPv6SnoopingTableSrvPort OBJECT-TYPE
		SYNTAX    INTEGER
		ACCESS    read-only
		STATUS    mandatory
		DESCRIPTION
			"Server Port Number"
		::= { swhDHCPv6SnoopingTableEntry 3 }

	swhDHCPv6SnoopingTableVID OBJECT-TYPE
		SYNTAX    INTEGER
		ACCESS    read-only
		STATUS    mandatory
		DESCRIPTION
			"VLAN ID"
		::= { swhDHCPv6SnoopingTableEntry 4 }

	swhDHCPv6SnoopingTableCliIPAddr OBJECT-TYPE
		SYNTAX    DisplayString
		ACCESS    read-only
		STATUS    mandatory
		DESCRIPTION
			"IPv6 Address"
		::= { swhDHCPv6SnoopingTableEntry 5 }

	swhDHCPv6SnoopingTableCliMacAddr OBJECT-TYPE
		SYNTAX    MacAddress
		ACCESS    read-only
		STATUS    mandatory
		DESCRIPTION
			"Client Mac Address"
		::= { swhDHCPv6SnoopingTableEntry 6 }

	swhDHCPv6SnoopingTableSrvIPAddr OBJECT-TYPE
		SYNTAX    DisplayString
		ACCESS    read-only
		STATUS    mandatory
		DESCRIPTION
			"IPv6 Address"
		::= { swhDHCPv6SnoopingTableEntry 7 }

	swhDHCPv6SnoopingTableTimeLeft OBJECT-TYPE
		SYNTAX    DisplayString
		ACCESS    read-only
		STATUS    mandatory
		DESCRIPTION
			"UpTime"
		::= { swhDHCPv6SnoopingTableEntry 8 }

--	swhDHCPv6SnoopingTableIPSourceGuardUnlimited OBJECT-TYPE
--		SYNTAX    DisplayString
--		ACCESS    read-only
--		STATUS    mandatory
--		DESCRIPTION
--			"IP Source Guard Unlimited"
--		::= { swhDHCPv6SnoopingTableEntry 9 }


-- SwitchMonitor(5).LoopDetectionStatus(36)

	swhLoopDetectionStatusUpdate OBJECT-TYPE
		SYNTAX    INTEGER { normal(0), update(1) }
		ACCESS    read-write
		STATUS    mandatory
		DESCRIPTION
			"Update Loop Status Table."
		::= { swhLoopDetectionStatus 2 }


-- SwitchMonitor(5).LoopDetectionStatus(36).LoopDetectionStatusTable(4)

	swhLoopDetectionStatusTable OBJECT-TYPE
		SYNTAX    SEQUENCE OF SwhLoopDetectionStatusEntry
		ACCESS    not-accessible
		STATUS    mandatory
		DESCRIPTION
			"Table of Loop Status."
		::= { swhLoopDetectionStatus 4 }

 	-- Table Entry
	swhLoopDetectionStatusEntry OBJECT-TYPE
		SYNTAX    SwhLoopDetectionStatusEntry
		ACCESS    not-accessible
		STATUS    mandatory
		DESCRIPTION
			"An entry in the table, containing information
			about Loop Status table"
		INDEX    { swhLoopDetectionStatusPort }
		::= { swhLoopDetectionStatusTable 1 }

	SwhLoopDetectionStatusEntry ::=
		SEQUENCE {
			swhLoopDetectionStatusPort
				INTEGER,
			swhLoopDetectionStatusStatus
				INTEGER,
			swhLoopDetectionStatusLockCause
				DisplayString,
			swhLoopDetectionStatusUnlock
				INTEGER
		}

	swhLoopDetectionStatusPort OBJECT-TYPE
		SYNTAX    INTEGER (0..2147483647)
		ACCESS    not-accessible
		STATUS    mandatory
		DESCRIPTION
			"A unique value for Port index."
		::= { swhLoopDetectionStatusEntry 1 }

	swhLoopDetectionStatusLockCause OBJECT-TYPE
		SYNTAX    DisplayString
		ACCESS    read-only
		STATUS    mandatory
		DESCRIPTION
			"Lock Cause."
		::= { swhLoopDetectionStatusEntry 3 }

	swhLoopDetectionStatusStatus OBJECT-TYPE
		SYNTAX    INTEGER { na2(-2), na(-1), un-lock(0), lock(1) }
		ACCESS    read-only
		STATUS    mandatory
		DESCRIPTION
			"Status."
		::= { swhLoopDetectionStatusEntry 4 }

	swhLoopDetectionStatusUnlock OBJECT-TYPE
		SYNTAX    INTEGER { normal(0), unlock(1) }
		ACCESS    read-write
		STATUS    mandatory
		DESCRIPTION
			"Unlock."
		::= { swhLoopDetectionStatusEntry 9 }


-- SwitchMonitor(5).MacLimitersStatus(39)
--
--	swhMacLimitersStatusTable OBJECT-TYPE
--		SYNTAX    SEQUENCE OF SwhMacLimitersStatusEntry
--		ACCESS    not-accessible
--		STATUS    mandatory
--		DESCRIPTION
--			"Table of MAC Limit Status."
--		::= { swhMacLimitersStatus 1 }
--
 	-- Table Entry
--	swhMacLimitersStatusEntry OBJECT-TYPE
--		SYNTAX    SwhMacLimitersStatusEntry
--		ACCESS    not-accessible
--		STATUS    mandatory
--		DESCRIPTION
--			"An entry in the table, containing information
--			about MAC Limit Status table"
--		INDEX    { swhMacLimitersStatusPort }
--		::= { swhMacLimitersStatusTable 1 }
--
--	SwhMacLimitersStatusEntry ::=
--		SEQUENCE {
--			swhMacLimitersStatusPort
--				INTEGER,
--			swhMacLimitersStatusLimit
--				INTEGER,
--			swhMacLimitersStatusCurrent
--				INTEGER
--		}
--
--	swhMacLimitersStatusPort OBJECT-TYPE
--		SYNTAX    INTEGER (0..2147483647)
--		ACCESS    not-accessible
--		STATUS    mandatory
--		DESCRIPTION
--			"A unique value for Port index."
--		::= { swhMacLimitersStatusEntry 1 }
--
--	swhMacLimitersStatusLimit OBJECT-TYPE
--		SYNTAX    INTEGER { na(-1), unlocked(0), lock(1) }
--		ACCESS    read-only
--		STATUS    mandatory
--		DESCRIPTION
--			"Limit."
--		::= { swhMacLimitersStatusEntry 2 }
--
--	swhMacLimitersStatusCurrent OBJECT-TYPE
--		SYNTAX    INTEGER { na(-1) }
--		ACCESS    read-only
--		STATUS    mandatory
--		DESCRIPTION
--			"Current."
--		::= { swhMacLimitersStatusEntry 3 }


-- SwitchMonitor(5).MacAddressStore(40)


-- SwitchMonitor(5).MacAddressStore(40).MacStoreTable(6)


-- SwitchMonitor(5).DODIStatus(41).DIStatus(1)

--	swhDIStatusTable OBJECT-TYPE
--		SYNTAX    SEQUENCE OF SwhDIStatusEntry
--		ACCESS    not-accessible
--		STATUS    mandatory
--		DESCRIPTION
--			"Table of digital input status."
--		::= { swhDIStatus 1 }
--
	-- Table Entry
--	swhDIStatusEntry OBJECT-TYPE
--		SYNTAX    SwhDIStatusEntry
--		ACCESS    not-accessible
--		STATUS    mandatory
--		DESCRIPTION
--			"An entry in the table, containing information
--			about digital input status"
--		INDEX    { swhDIStatusIndex }
--		::= { swhDIStatusTable 1 }
--
--	SwhDIStatusEntry ::=
--		SEQUENCE {
--			swhDIStatusIndex
--				INTEGER,
		--	swhDIStatusNormal
		--		INTEGER,
--			swhDIStatusStatus
--				INTEGER,
--			swhDIStatusAlarm
--				INTEGER
--		}
--
--	swhDIStatusIndex OBJECT-TYPE
--		SYNTAX    INTEGER (0..2147483647)
--		ACCESS    not-accessible
--		STATUS    mandatory
--		DESCRIPTION
--			"A unique value for digital input index."
--		::= { swhDIStatusEntry 1 }
--
--	swhDIStatusNormal OBJECT-TYPE
--		SYNTAX    INTEGER { close(0), open(1) }
--		ACCESS    read-only
--		STATUS    mandatory
--		DESCRIPTION
--			"digital input normal."
--		::= { swhDIStatusEntry 2 }
--
--	swhDIStatusStatus OBJECT-TYPE
--		SYNTAX    INTEGER { close(0), open(1) }
--		ACCESS    read-only
--		STATUS    mandatory
--		DESCRIPTION
--			"digital input status."
--		::= { swhDIStatusEntry 3 }
--
--	swhDIStatusAlarm OBJECT-TYPE
--		SYNTAX    INTEGER { off(0), on(1) }
--		ACCESS    read-only
--		STATUS    mandatory
--		DESCRIPTION
--			"digital input alarm."
--		::= { swhDIStatusEntry 4 }


-- SwitchMonitor(5).DODIStatus(41).DOStatus(2)


-- SwitchMonitor(5).DODIStatus(41).DOPortStatus(2)


-- SwitchMonitor(5).RingStatus(43).RingStatusTable(1)


-- SwitchMonitor(5).CPUAndMemoryStatistics(45)

	swhCPUStatistics
		OBJECT IDENTIFIER ::= { swhCPUAndMemoryStatistics 1 }
	swhMemoryStatistics
		OBJECT IDENTIFIER ::= { swhCPUAndMemoryStatistics 2 }


-- SwitchMonitor(5).CPUAndMemoryStatistics(45).CPUStatistics(1)

	swhCPUStatisticsCPULoadingThreshold OBJECT-TYPE
		SYNTAX    INTEGER (1..65535)
		ACCESS    read-write
		STATUS    mandatory
		DESCRIPTION
			"CPU Loading Threshold"
		::= { swhCPUStatistics 1 }

	swhCPUStatisticsCPUUsage OBJECT-TYPE
		SYNTAX    DisplayString
		ACCESS    read-only
		STATUS    mandatory
		DESCRIPTION
			"CPU Usage (%)"
		::= { swhCPUStatistics 2 }

	swhCPUStatisticsLoadAverages1min OBJECT-TYPE
		SYNTAX    DisplayString
		ACCESS    read-only
		STATUS    mandatory
		DESCRIPTION
			"Load Averages - 1 min"
		::= { swhCPUStatistics 5 }

	swhCPUStatisticsLoadAverages5min OBJECT-TYPE
		SYNTAX    DisplayString
		ACCESS    read-only
		STATUS    mandatory
		DESCRIPTION
			"Load Averages - 5 min"
		::= { swhCPUStatistics 6 }

	swhCPUStatisticsLoadAverages15min OBJECT-TYPE
		SYNTAX    DisplayString
		ACCESS    read-only
		STATUS    mandatory
		DESCRIPTION
			"Load Averages - 15 min"
		::= { swhCPUStatistics 7 }


-- SwitchMonitor(5).CPUAndMemoryStatistics(45).MemoryStatistics(2)

	swhMemoryStatisticsTotalMemory OBJECT-TYPE
		SYNTAX    DisplayString
		ACCESS    read-only
		STATUS    mandatory
		DESCRIPTION
			"Total Memory(KByte)"
		::= { swhMemoryStatistics 5 }

	swhMemoryStatisticsMemoryUse OBJECT-TYPE
		SYNTAX    DisplayString
		ACCESS    read-only
		STATUS    mandatory
		DESCRIPTION
			"Memory Use(KByte)"
		::= { swhMemoryStatistics 6 }

	swhMemoryStatisticsMemoryFree OBJECT-TYPE
		SYNTAX    DisplayString
		ACCESS    read-only
		STATUS    mandatory
		DESCRIPTION
			"Memory Free(KByte)"
		::= { swhMemoryStatistics 7 }

	swhMemoryStatisticsMemoryBuffers OBJECT-TYPE
		SYNTAX    DisplayString
		ACCESS    read-only
		STATUS    mandatory
		DESCRIPTION
			"Memory Buffers(KByte)"
		::= { swhMemoryStatistics 8 }

	swhMemoryStatisticsMemoryCached OBJECT-TYPE
		SYNTAX    DisplayString
		ACCESS    read-only
		STATUS    mandatory
		DESCRIPTION
			"Memory Cached(KByte)"
		::= { swhMemoryStatistics 9 }


-- SwitchMonitor(5).POEStatus(48)

-- SwitchMonitor(5).CPUTemperatureStatus(51)

	swhCPUHighTemperatureThreshold OBJECT-TYPE
		SYNTAX    INTEGER (0..2147483647)
		ACCESS    read-write
		STATUS    mandatory
		DESCRIPTION
			"High Temperature Threshold(C)"
		::= { swhCPUTemperatureStatus 1 }

	swhCPUThresholdInterval OBJECT-TYPE
		SYNTAX    INTEGER (0..2147483647)
		ACCESS    read-write
		STATUS    mandatory
		DESCRIPTION
			"Threshold Interval(120-86400)"
		::= { swhCPUTemperatureStatus 2 }

	swhCPUContinuousAlarm OBJECT-TYPE
		SYNTAX    INTEGER { disable(0), enable(1) }
		ACCESS    read-write
		STATUS    mandatory
		DESCRIPTION
			"Enable or disable Continuous Alarm"
		::= { swhCPUTemperatureStatus 3 }

	swhCPUCurrentCPUTemperature OBJECT-TYPE
		SYNTAX    Integer32 (-2147483648..2147483647)
		ACCESS    read-only
		STATUS    mandatory
		DESCRIPTION
			"Current CPU Temperature(1/10 )"
		::= { swhCPUTemperatureStatus 5 }

	swhCPUHistoricalHighCPUTemperature OBJECT-TYPE
		SYNTAX    Integer32 (-2147483648..2147483647)
		ACCESS    read-only
		STATUS    mandatory
		DESCRIPTION
			"Historical High CPU Temperature(1/10 )"
		::= { swhCPUTemperatureStatus 6 }

	swhCPUHistoricalHighElapsedTime OBJECT-TYPE
		SYNTAX    DisplayString (SIZE (0..255))
		ACCESS    read-only
		STATUS    mandatory
		DESCRIPTION
			"Historical High Elapsed Time"
		::= { swhCPUTemperatureStatus 7 }

	swhCPUHistoricalLowCPUTemperature OBJECT-TYPE
		SYNTAX    Integer32 (-2147483648..2147483647)
		ACCESS    read-only
		STATUS    mandatory
		DESCRIPTION
			"Historical Low CPU Temperature(1/10 )"
		::= { swhCPUTemperatureStatus 8 }

	swhCPUHistoricalLowElapsedTime OBJECT-TYPE
		SYNTAX    DisplayString (SIZE (0..255))
		ACCESS    read-only
		STATUS    mandatory
		DESCRIPTION
			"Historical Low Elapsed Time"
		::= { swhCPUTemperatureStatus 9 }


-- SwitchMonitor(5).FastRedundancyStatus(52)


-- SwitchMonitor(5).FanSpeedState(54).FanSpeedStateTable(1)

--	swhFanSpeedStateTable OBJECT-TYPE
--		SYNTAX    SEQUENCE OF SwhFanSpeedStateEntry
--		ACCESS    not-accessible
--		STATUS    mandatory
--		DESCRIPTION
--			"Table of Fan Speed state."
--		::= { swhFanSpeedState 1 }

	-- Table Entry
--	swhFanSpeedStateEntry OBJECT-TYPE
--		SYNTAX    SwhFanSpeedStateEntry
--		ACCESS    not-accessible
--		STATUS    mandatory
--		DESCRIPTION
--			"An entry in the table, containing information
--			about Fan Speed state"
--		INDEX    { swhFanSpeedStateIndex }
--		::= { swhFanSpeedStateTable 1 }

--	SwhFanSpeedStateEntry ::=
--		SEQUENCE {
--			swhFanSpeedStateIndex
--				INTEGER,
--			swhFanSpeedStateCurrent
--				INTEGER,
--			swhFanSpeedStateThresholdHigh
--				INTEGER,
--			swhFanSpeedStateThresholdLow
--				INTEGER,
--			swhFanSpeedStateState
--				DisplayString
--		}

--	swhFanSpeedStateIndex OBJECT-TYPE
--		SYNTAX    INTEGER (0..2147483647)
--		ACCESS    not-accessible
--		STATUS    mandatory
--		DESCRIPTION
--			"A unique value for Fan index."
--		::= { swhFanSpeedStateEntry 1 }

--	swhFanSpeedStateCurrent OBJECT-TYPE
--		SYNTAX    INTEGER (0..2147483647)
--		ACCESS    read-only
--		STATUS    mandatory
--		DESCRIPTION
--			"Fan Speed Current."
--		::= { swhFanSpeedStateEntry 2 }

--	swhFanSpeedStateThresholdHigh OBJECT-TYPE
--		SYNTAX    INTEGER (0..2147483647)
--		ACCESS    read-only
--		STATUS    mandatory
--		DESCRIPTION
--			"Fan Speed Threshold High"
--		::= { swhFanSpeedStateEntry 3 }

--	swhFanSpeedStateThresholdLow OBJECT-TYPE
--		SYNTAX    INTEGER (0..2147483647)
--		ACCESS    read-only
--		STATUS    mandatory
--		DESCRIPTION
--			"Fan Speed Threshold Low"
--		::= { swhFanSpeedStateEntry 4 }

--	swhFanSpeedStateState OBJECT-TYPE
--		SYNTAX    DisplayString
--		ACCESS    read-only
--		STATUS    mandatory
--		DESCRIPTION
--			"Fan Speed State"
--		::= { swhFanSpeedStateEntry 5 }


-- SwitchMonitor(5).SystemVoltageState(52).SystemVoltageStateTable(1)

--	swhSystemVoltageStateTable OBJECT-TYPE
--		SYNTAX    SEQUENCE OF SwhSystemVoltageStateEntry
--		ACCESS    not-accessible
--		STATUS    mandatory
--		DESCRIPTION
--			"Table of Voltage state."
--		::= { swhSystemVoltageState 1 }

	-- Table Entry
--	swhSystemVoltageStateEntry OBJECT-TYPE
--		SYNTAX    SwhSystemVoltageStateEntry
--		ACCESS    not-accessible
--		STATUS    mandatory
--		DESCRIPTION
--			"An entry in the table, containing information
--			about Voltage state"
--		INDEX    { swhSystemVoltageStateIndex }
--		::= { swhSystemVoltageStateTable 1 }

--	SwhSystemVoltageStateEntry ::=
--		SEQUENCE {
--			swhSystemVoltageStateIndex
--				INTEGER,
--			swhSystemVoltageStateComponent
--				INTEGER,
--			swhSystemVoltageStateCurrent
--				INTEGER,
--			swhSystemVoltageStateThresholdHigh
--				INTEGER,
--			swhSystemVoltageStateThresholdLow
--				INTEGER,
--			swhSystemVoltageStateState
--				DisplayString
--		}

--	swhSystemVoltageStateIndex OBJECT-TYPE
--		SYNTAX    INTEGER (0..2147483647)
--		ACCESS    not-accessible
--		STATUS    mandatory
--		DESCRIPTION
--			"A unique value for Voltage index."
--		::= { swhSystemVoltageStateEntry 1 }

--	swhSystemVoltageStateComponent OBJECT-TYPE
--		SYNTAX    DisplayString
--		ACCESS    read-only
--		STATUS    mandatory
--		DESCRIPTION
--			"Voltage Component."
--		::= { swhSystemVoltageStateEntry 2 }

--	swhSystemVoltageStateCurrent OBJECT-TYPE
--		SYNTAX    INTEGER (0..2147483647)
--		ACCESS    read-only
--		STATUS    mandatory
--		DESCRIPTION
--			"Voltage Current"
--		::= { swhSystemVoltageStateEntry 3 }

--	swhSystemVoltageStateThresholdHigh OBJECT-TYPE
--		SYNTAX    INTEGER (0..2147483647)
--		ACCESS    read-only
--		STATUS    mandatory
--		DESCRIPTION
--			"Voltage Threshold High"
--		::= { swhSystemVoltageStateEntry 4 }

--	swhSystemVoltageStateThresholdLow OBJECT-TYPE
--		SYNTAX    INTEGER (0..2147483647)
--		ACCESS    read-only
--		STATUS    mandatory
--		DESCRIPTION
--			"Voltage Threshold Low"
--		::= { swhSystemVoltageStateEntry 5 }

--	swhSystemVoltageStateState OBJECT-TYPE
--		SYNTAX    DisplayString
--		ACCESS    read-only
--		STATUS    mandatory
--		DESCRIPTION
--			"Voltage state."
--		::= { swhSystemVoltageStateEntry 6 }


-- SwitchMonitor(5).STPStatus(10).STPBridgeTable(7)

--	swhSTPStatusMSTI OBJECT-TYPE
--		SYNTAX    INTEGER { MSTI00(0),
--		                    MSTI01(1),
--		                    MSTI02(2),
--		                    MSTI03(3),
--		                    MSTI04(4),
--		                    MSTI05(5),
--		                    MSTI06(6),
--		                    MSTI07(7),
--		                    MSTI08(8),
--		                    MSTI09(9),
--		                    MSTI10(10),
--		                    MSTI11(11),
--		                    MSTI12(12),
--		                    MSTI13(13),
--		                    MSTI14(14),
--		                    MSTI15(15)
--		                    }
--		ACCESS    read-write
--		STATUS    mandatory
--		DESCRIPTION
--			"MSTI."
--		::= { swhSTPStatus 1 }
--
--
-- SwitchMonitor(5).STPStatus(56).STPBridgeTable(7)
--
--	swhSTPBridgeTable OBJECT-TYPE
--		SYNTAX    SEQUENCE OF SwhSTPBridgeEntry
--		ACCESS    not-accessible
--		STATUS    mandatory
--		DESCRIPTION
--			"Table of STP Bridge Overview."
--		::= { swhSTPStatus 7 }
--
	-- Table Entry
--	swhSTPBridgeEntry OBJECT-TYPE
--		SYNTAX    SwhSTPBridgeEntry
--		ACCESS    not-accessible
--		STATUS    mandatory
--		DESCRIPTION
--			"An entry in the table, containing information
--			about STP Bridge mode."
--		INDEX    { swhSTPBridgeIndex }
--		::= { swhSTPBridgeTable 1 }
--
--	SwhSTPBridgeEntry ::=
--		SEQUENCE {
--			swhSTPBridgeIndex
--				INTEGER,
--			swhSTPBridgeBridgeID
--				DisplayString,
--			swhSTPBridgeMaxAge
--				INTEGER,
--			swhSTPBridgeHelloTime
--				INTEGER,
--			swhSTPBridgeFwdDelay
--				INTEGER,
--			swhSTPBridgeTopology
--				INTEGER,
--			swhSTPBridgeRootID
--				DisplayString,
--			swhSTPBridgeRootPort
--				DisplayString,
--			swhSTPBridgeLastTCTime
--				DisplayString,
--			swhSTPBridgeElapsedTime
--				INTEGER
--		}
--
--	swhSTPBridgeIndex OBJECT-TYPE
--		SYNTAX    INTEGER (0..2147483647)
--		ACCESS    not-accessible
--		STATUS    mandatory
--		DESCRIPTION
--			"A unique value for each Port."
--		::= { swhSTPBridgeEntry 1 }
--
--	swhSTPBridgeBridgeID OBJECT-TYPE
--		SYNTAX    DisplayString
--		ACCESS    read-only
--		STATUS    mandatory
--		DESCRIPTION
--			"Bridge ID"
--		::= { swhSTPBridgeEntry 3 }
--
--	swhSTPBridgeMaxAge OBJECT-TYPE
--		SYNTAX    INTEGER
--		ACCESS    read-only
--		STATUS    mandatory
--		DESCRIPTION
--			"Max Age"
--		::= { swhSTPBridgeEntry 4 }
--
--	swhSTPBridgeHelloTime OBJECT-TYPE
--		SYNTAX    INTEGER
--		ACCESS    read-only
--		STATUS    mandatory
--		DESCRIPTION
--			"Hello Time"
--		::= { swhSTPBridgeEntry 5 }
--
--	swhSTPBridgeFwdDelay OBJECT-TYPE
--		SYNTAX    INTEGER
--		ACCESS    read-only
--		STATUS    mandatory
--		DESCRIPTION
--			"Fwd Delay"
--		::= { swhSTPBridgeEntry 6 }
--
--	swhSTPBridgeTopology OBJECT-TYPE
--		SYNTAX    INTEGER { steady(0), changing(1) }
--		ACCESS    read-only
--		STATUS    mandatory
--		DESCRIPTION
--			"Topology"
--		::= { swhSTPBridgeEntry 7 }
--
--	swhSTPBridgeRootID OBJECT-TYPE
--		SYNTAX    DisplayString
--		ACCESS    read-only
--		STATUS    mandatory
--		DESCRIPTION
--			"Root ID"
--		::= { swhSTPBridgeEntry 10 }
--
--	swhSTPBridgeRootPort OBJECT-TYPE
--		SYNTAX    DisplayString
--		ACCESS    read-only
--		STATUS    mandatory
--		DESCRIPTION
--			"Root Port"
--		::= { swhSTPBridgeEntry 13 }
--
--	swhSTPBridgeLastTCTime OBJECT-TYPE
--		SYNTAX    DisplayString
--		ACCESS    read-only
--		STATUS    mandatory
--		DESCRIPTION
--			"Port Name"
--		::= { swhSTPBridgeEntry 15 }
--
--	swhSTPBridgeElapsedTime OBJECT-TYPE
--		SYNTAX    INTEGER (0..2147483647)
--		ACCESS    read-only
--		STATUS    mandatory
--		DESCRIPTION
--			"Port Name"
--		::= { swhSTPBridgeEntry 17 }
--
--
-- SwitchMonitor(5).STPStatus(56).STPPortStatusTable(9)
--
--	swhSTPPortStatusTable OBJECT-TYPE
--		SYNTAX    SEQUENCE OF SwhSTPPortStatusEntry
--		ACCESS    not-accessible
--		STATUS    mandatory
--		DESCRIPTION
--			"Table of STP Port Status."
--		::= { swhSTPStatus 9 }
--
	-- Table Entry
--	swhSTPPortStatusEntry OBJECT-TYPE
--		SYNTAX    SwhSTPPortStatusEntry
--		ACCESS    not-accessible
--		STATUS    mandatory
--		DESCRIPTION
--			"An entry in the table, containing information
--			about STP Port Status mode."
--		INDEX    { swhSTPPortStatusIndex }
--		::= { swhSTPPortStatusTable 1 }
--
--	SwhSTPPortStatusEntry ::=
--		SEQUENCE {
--			swhSTPPortStatusIndex
--				INTEGER,
--			swhSTPPortStatusPort
--				DisplayString,
--			swhSTPPortStatusPathCost
--				INTEGER,
--			swhSTPPortStatusEdgePort
--				INTEGER,
--			swhSTPPortStatusP2pPort
--				INTEGER,
--			swhSTPPortStatusProtocol
--				INTEGER,
--			swhSTPPortStatusRole
--				INTEGER,
--			swhSTPPortStatusPortState
--				INTEGER
--		}
--
--	swhSTPPortStatusIndex OBJECT-TYPE
--		SYNTAX    INTEGER (0..2147483647)
--		ACCESS    not-accessible
--		STATUS    mandatory
--		DESCRIPTION
--			"A unique value for each Port."
--		::= { swhSTPPortStatusEntry 1 }
--
--	swhSTPPortStatusPathCost OBJECT-TYPE
--		SYNTAX    INTEGER
--		ACCESS    read-only
--		STATUS    mandatory
--		DESCRIPTION
--			"Path Cost"
--		::= { swhSTPPortStatusEntry 3 }
--
--	swhSTPPortStatusEdgePort OBJECT-TYPE
--		SYNTAX    INTEGER { no(0), yes(1) }
--		ACCESS    read-only
--		STATUS    mandatory
--		DESCRIPTION
--			"Edge Port"
--		::= { swhSTPPortStatusEntry 4 }
--
--	swhSTPPortStatusP2pPort OBJECT-TYPE
--		SYNTAX    INTEGER { no(0), yes(1) }
--		ACCESS    read-only
--		STATUS    mandatory
--		DESCRIPTION
--			"P2p Port"
--		::= { swhSTPPortStatusEntry 5 }
--
--	swhSTPPortStatusProtocol OBJECT-TYPE
--		SYNTAX    INTEGER { stp(0), rstp(2), mstp(3) }
--		ACCESS    read-only
--		STATUS    mandatory
--		DESCRIPTION
--			"Protocol"
--		::= { swhSTPPortStatusEntry 6 }
--
--	swhSTPPortStatusRole OBJECT-TYPE
--		SYNTAX    INTEGER { disable(0), alternate(1), backup(2), root(3), designated(4), non-stp(5), master(6) }
--		ACCESS    read-only
--		STATUS    mandatory
--		DESCRIPTION
--			"Role"
--		::= { swhSTPPortStatusEntry 7 }
--
--	swhSTPPortStatusPortState OBJECT-TYPE
--		SYNTAX    INTEGER { disable(0), blocking(1), listening(2), learning(3), forwarding(4), non-stp(5) }
--		ACCESS    read-only
--		STATUS    mandatory
--		DESCRIPTION
--			"Port State"
--		::= { swhSTPPortStatusEntry 8 }
--
--	swhSTPPortStatusPort OBJECT-TYPE
--		SYNTAX    DisplayString
--		ACCESS    read-only
--		STATUS    mandatory
--		DESCRIPTION
--			"Port Name"
--		::= { swhSTPPortStatusEntry 9 }
--
--
-- SwitchMonitor(5).STPStatus(56).STPStatisticsTable(1)
--
--	swhSTPStatisticsTable OBJECT-TYPE
--		SYNTAX    SEQUENCE OF SwhSTPStatisticsEntry
--		ACCESS    not-accessible
--		STATUS    mandatory
--		DESCRIPTION
--			"Table of STP Statistics."
--		::= { swhSTPStatus 11 }
--
	-- Table Entry
--	swhSTPStatisticsEntry OBJECT-TYPE
--		SYNTAX    SwhSTPStatisticsEntry
--		ACCESS    not-accessible
--		STATUS    mandatory
--		DESCRIPTION
--			"An entry in the table, containing information
--			about STP Statistics."
--		INDEX    { swhSTPStatisticsIndex }
--		::= { swhSTPStatisticsTable 1 }
--
--	SwhSTPStatisticsEntry ::=
--		SEQUENCE {
--			swhSTPStatisticsIndex
--				INTEGER,
--			swhSTPStatisticsPort
--				DisplayString,
--			swhSTPStatisticsMSTPTx
--				Counter,
--			swhSTPStatisticsMSTPRx
--				Counter,
--			swhSTPStatisticsRSTPTx
--				Counter,
--			swhSTPStatisticsRSTPRx
--				Counter,
--			swhSTPStatisticsSTPTx
--				Counter,
--			swhSTPStatisticsSTPRx
--				Counter,
--			swhSTPStatisticsTCNTx
--				Counter,
--			swhSTPStatisticsTCNRx
--				Counter,
--			swhSTPStatisticsIllegalRx
--				Counter,
--			swhSTPStatisticsUnknownRx
--				Counter
--		}
--
--	swhSTPStatisticsIndex OBJECT-TYPE
--		SYNTAX    INTEGER (0..2147483647)
--		ACCESS    not-accessible
--		STATUS    mandatory
--		DESCRIPTION
--			"A unique value for each Port."
--		::= { swhSTPStatisticsEntry 1 }
--
--	swhSTPStatisticsMSTPTx OBJECT-TYPE
--		SYNTAX    Counter
--		ACCESS    read-only
--		STATUS    mandatory
--		DESCRIPTION
--			""
--		::= { swhSTPStatisticsEntry 3 }
--
--	swhSTPStatisticsMSTPRx OBJECT-TYPE
--		SYNTAX    Counter
--		ACCESS    read-only
--		STATUS    mandatory
--		DESCRIPTION
--			""
--		::= { swhSTPStatisticsEntry 5 }
--
--	swhSTPStatisticsRSTPTx OBJECT-TYPE
--		SYNTAX    Counter
--		ACCESS    read-only
--		STATUS    mandatory
--		DESCRIPTION
--			""
--		::= { swhSTPStatisticsEntry 7 }
--
--	swhSTPStatisticsRSTPRx OBJECT-TYPE
--		SYNTAX    Counter
--		ACCESS    read-only
--		STATUS    mandatory
--		DESCRIPTION
--			""
--		::= { swhSTPStatisticsEntry 9 }
--
--	swhSTPStatisticsSTPTx OBJECT-TYPE
--		SYNTAX    Counter
--		ACCESS    read-only
--		STATUS    mandatory
--		DESCRIPTION
--			""
--		::= { swhSTPStatisticsEntry 11 }
--
--	swhSTPStatisticsSTPRx OBJECT-TYPE
--		SYNTAX    Counter
--		ACCESS    read-only
--		STATUS    mandatory
--		DESCRIPTION
--			""
--		::= { swhSTPStatisticsEntry 13 }
--
--	swhSTPStatisticsTCNTx OBJECT-TYPE
--		SYNTAX    Counter
--		ACCESS    read-only
--		STATUS    mandatory
--		DESCRIPTION
--			""
--		::= { swhSTPStatisticsEntry 15 }
--
--	swhSTPStatisticsTCNRx OBJECT-TYPE
--		SYNTAX    Counter
--		ACCESS    read-only
--		STATUS    mandatory
--		DESCRIPTION
--			""
--		::= { swhSTPStatisticsEntry 17 }
--
--	swhSTPStatisticsIllegalRx OBJECT-TYPE
--		SYNTAX    Counter
--		ACCESS    read-only
--		STATUS    mandatory
--		DESCRIPTION
--			""
--		::= { swhSTPStatisticsEntry 19 }
--
--	swhSTPStatisticsUnknownRx OBJECT-TYPE
--		SYNTAX    Counter
--		ACCESS    read-only
--		STATUS    mandatory
--		DESCRIPTION
--			""
--		::= { swhSTPStatisticsEntry 21 }
--
--	swhSTPStatisticsPort OBJECT-TYPE
--		SYNTAX    DisplayString
--		ACCESS    read-only
--		STATUS    mandatory
--		DESCRIPTION
--			"Port Name"
--		::= { swhSTPStatisticsEntry 23 }


-- SystemUtility(6)

	swhLoadFactorySetting OBJECT-TYPE
		SYNTAX    INTEGER { normal(0), load(1) }
		ACCESS    read-write
		STATUS    mandatory
		DESCRIPTION
			"LoadFactorySetting"
		::= { swhSystemUtility 1 }

	swhLoadFactorySettingExceptNetworkConfiguration OBJECT-TYPE
		SYNTAX    INTEGER { normal(0), load(1) }
		ACCESS    read-write
		STATUS    mandatory
		DESCRIPTION
			"LoadFactorySettingExceptNetworkConfiguration"
		::= { swhSystemUtility 2 }

	swhEventLog
		OBJECT IDENTIFIER ::= { swhSystemUtility 3 }
	swhPortLinkFlapLog
		OBJECT IDENTIFIER ::= { swhSystemUtility 9 }
	swhLEDControl
		OBJECT IDENTIFIER ::= { swhSystemUtility 11 }
	swhUpdateFirmware
		OBJECT IDENTIFIER ::= { swhSystemUtility 4 }
--	swhFirmwareCopy
--		OBJECT IDENTIFIER ::= { swhSystemUtility 8 }
	swhAutoBackupConfiguration
		OBJECT IDENTIFIER ::= { swhSystemUtility 5 }
--	swhBackupConfiguration
--		OBJECT IDENTIFIER ::= { swhSystemUtility 5 }
--	swhLoopbackTest
--		OBJECT IDENTIFIER ::= { swhSystemUtility 6 }


-- SystemUtility(6).EventLog(3)

	swhEventLogTable OBJECT-TYPE
		SYNTAX    SEQUENCE OF SwhEventLogEntry
		ACCESS    not-accessible
		STATUS    mandatory
		DESCRIPTION
			"Table of Event Log."
		::= { swhEventLog 1 }

	swhEventLogClear OBJECT-TYPE
		SYNTAX    INTEGER { normal(0), clear(1) }
		ACCESS    read-write
		STATUS    mandatory
		DESCRIPTION
			"Clear Event Log Table"
		::= { swhEventLog 2 }

	-- Table Entry
	swhEventLogEntry OBJECT-TYPE
		SYNTAX    SwhEventLogEntry
		ACCESS    not-accessible
		STATUS    mandatory
		DESCRIPTION
			"An entry in the table, containing information
			about Event Log"
		INDEX    { swhEventLogIndex }
		::= { swhEventLogTable 1 }

	SwhEventLogEntry ::=
		SEQUENCE {
			swhEventLogIndex
				INTEGER,
			swhEventLogNumber
				INTEGER,
			swhEventLogType
				INTEGER,
			swhEventLogTime
				DisplayString,
			swhEventLogUpTime
				DisplayString,
			swhEventLogDescription
				DisplayString,
			swhEventLogSource
				INTEGER,
			swhEventLogEvent
				INTEGER,
			swhEventLogNameCommunity
				DisplayString,
			swhEventLogIPAddr
				DisplayString
		--	swhEventLogCategory
		--		INTEGER
		}

	swhEventLogIndex OBJECT-TYPE
		SYNTAX    INTEGER (0..2147483647)
		ACCESS    not-accessible
		STATUS    mandatory
		DESCRIPTION
			"A unique value for Event Log  index."
		::= { swhEventLogEntry 1 }

	swhEventLogType OBJECT-TYPE
		SYNTAX    INTEGER { error(1000), warning(2000), information(3000) }
		ACCESS    read-only
		STATUS    mandatory
		DESCRIPTION
			"event type
			error: some funtions not work
			warning: to warn something, ex. login failed
			information: just something happened
			"
		::= { swhEventLogEntry 2 }

	swhEventLogTime OBJECT-TYPE
		SYNTAX    DisplayString
		ACCESS    read-only
		STATUS    mandatory
		DESCRIPTION
			"event happening time,
			it is local time"
		::= { swhEventLogEntry 3 }

	swhEventLogUpTime OBJECT-TYPE
		SYNTAX    DisplayString
		ACCESS    read-only
		STATUS    mandatory
		DESCRIPTION
			"event happening time,
			it is system up time
			"
		::= { swhEventLogEntry 4 }

	swhEventLogDescription OBJECT-TYPE
		SYNTAX    DisplayString
		ACCESS    read-only
		STATUS    mandatory
		DESCRIPTION
			"event description"
		::= { swhEventLogEntry 5 }

	swhEventLogSource OBJECT-TYPE
		SYNTAX    INTEGER { local-machine(4000),
		                    rs232d(4001),
		                    rs232(4002),
		                    telnetd(4003),
		                    telnet(4004),
		                    tftpd(4005),
		                    tftp(4006),
		                    ftpd(4007),
		                    ftp(4008),
		                    snmpd(4009),
		                    snmp(4010),
		                    webd(4011),
		                    web(4012),
		                    ping(4013),
		                    watch-dog(4014),
		                    remote-machine(4015),
		                    catv-module(4016),
							ssh(4020)
		                    }
		ACCESS    read-only
		STATUS    mandatory
		DESCRIPTION
			"event source"
		::= { swhEventLogEntry 6 }

	swhEventLogEvent OBJECT-TYPE
		SYNTAX    INTEGER { boot-failed(1001),
		                    load-config-failed(1002),
		                    load-default-config-failed(1003),
		                    save-config-failed(1004),
		                    save-default-config-failed(1005),
		                    login-failed(2001),
		                    module-down(2002),
		                    module-power-down(2003),
		                    power-module-down(2004),
		                    power-fan-failed(2005),
		                    backup-config-failed(2006),
		                    auto-provision(2007),
		                    fan-failed(2008),
		                    temperature-abnormality(2009),
		                    voltage-abnormality(2010),
		                    tx-bias-abnormality(2011),
		                    loop(2012),
		                    upgrade(2013),
		                    digital-input(2015),
		                    digital-output(2016),
		                    mac-limiters(2025),
		                    storm-control(2026),
		                    cpu-temperature-overheat(2027),
		                    cpu-temperature-failed(2028),
		                    fan-warning(2030),
		                    voltage-warning(2031),
		                    memory-low(2041),
		                    cold-start(3001),
		                    warm-start(3002),
		                    login(3003),
		                    logout(3004),
		                    timeout(3005),
		                    disconnected(3006),
		                    link-up(3007),
		                    link-down(3008),
		                    power-supply-up(3011),
		                    backup-config-succeeded(3020),
		                    fan-ok(3022),
		                    temperature-normality(3023),
		                    digital-input(3026),
		                    digital-output(3027),
		                    cpu-temperature-normal(3038),
							fast-redundancy-abnormal(3048),
							fast-redundancy-singalfail(3049),
							fast-redundancy-normal(3050)
		                    }
		ACCESS    read-only
		STATUS    mandatory
		DESCRIPTION
			"event"
		::= { swhEventLogEntry 7 }

	swhEventLogNameCommunity OBJECT-TYPE
		SYNTAX    DisplayString
		ACCESS    read-only
		STATUS    mandatory
		DESCRIPTION
			"user name or community name"
		::= { swhEventLogEntry 8 }

	swhEventLogIPAddr OBJECT-TYPE
		SYNTAX    DisplayString
		ACCESS    read-only
		STATUS    mandatory
		DESCRIPTION
			"event ip address,
			ex. login user ip address"
		::= { swhEventLogEntry 9 }

	swhEventLogNumber OBJECT-TYPE
		SYNTAX    INTEGER (0..2147483647)
		ACCESS    read-only
		STATUS    mandatory
		DESCRIPTION
			"A unique value for Event Log index number."
		::= { swhEventLogEntry 11 }

	--swhEventLogCategory OBJECT-TYPE
	--	SYNTAX    INTEGER (0..2147483647)
	--	ACCESS    read-only
	--	STATUS    mandatory
	--	DESCRIPTION
	--		"Category"
	--	::= { swhEventLogEntry 10 }


-- SystemUtility(6).UpdateFirmware(4)

	swhUpdateProtocol OBJECT-TYPE
		SYNTAX    INTEGER { tftp(0), ftp(1) }
		ACCESS    read-write
		STATUS    mandatory
		DESCRIPTION
			"Update file from tftp or ftp server."
		::= { swhUpdateFirmware 1 }

	swhUpdateFileType OBJECT-TYPE
		SYNTAX    INTEGER { firmware(0), configuration(1) }
		ACCESS    read-write
		STATUS    mandatory
		DESCRIPTION
			"Update file type."
		::= { swhUpdateFirmware 2 }

	swhUpdateConfigeType OBJECT-TYPE
		SYNTAX    INTEGER { running(0), default(1) , startup(2) }
		ACCESS    read-write
		STATUS    mandatory
		DESCRIPTION
			"Update confige type."
		::= { swhUpdateFirmware 15 }

	swhUpdateImageOption OBJECT-TYPE
		SYNTAX    INTEGER { image1(1), image2(2) }
		ACCESS    read-write
		STATUS    mandatory
		DESCRIPTION
			"Update Image Option."
		::= { swhUpdateFirmware 16 }

	swhUpdateServerIPAddr OBJECT-TYPE
		SYNTAX    IpAddress
		ACCESS    read-write
		STATUS    mandatory
		DESCRIPTION
			"Tftp/ftp server ip address."
		::= { swhUpdateFirmware 3 }

	swhUpdateServerIPv6Addr OBJECT-TYPE
		SYNTAX    DisplayString (SIZE (0..255))
		ACCESS    read-write
		STATUS    mandatory
		DESCRIPTION
			"Tftp/ftp server ipv6 address."
		::= { swhUpdateFirmware 13 }

	swhUpdateUserName OBJECT-TYPE
		SYNTAX    DisplayString (SIZE (0..255))
		ACCESS    read-write
		STATUS    mandatory
		DESCRIPTION
			"Ftp server login user name."
		::= { swhUpdateFirmware 4 }

	swhUpdatePassword OBJECT-TYPE
		SYNTAX    DisplayString (SIZE (0..255))
		ACCESS    read-write
		STATUS    mandatory
		DESCRIPTION
			"Ftp server login password."
		::= { swhUpdateFirmware 5 }

	swhUpdateFileLocation OBJECT-TYPE
		SYNTAX    DisplayString (SIZE (0..255))
		ACCESS    read-write
		STATUS    mandatory
		DESCRIPTION
			"Upate file location."
		::= { swhUpdateFirmware 6 }

	--swhUpdateGet OBJECT-TYPE
	--	SYNTAX    INTEGER { normal(0), get(1) }
	--	ACCESS    read-write
	--	STATUS    mandatory
	--	DESCRIPTION
	--		"Get file from server."
	--	::= { swhUpdateFirmware 7 }

	swhUpdatePut OBJECT-TYPE
		SYNTAX    INTEGER { normal(0), put(1) }
		ACCESS    read-write
		STATUS    mandatory
		DESCRIPTION
			"Put file to server."
		::= { swhUpdateFirmware 8 }

	swhUpdateUpdate OBJECT-TYPE
		SYNTAX    INTEGER { normal(0), update(1) }
		ACCESS    read-write
		STATUS    mandatory
		DESCRIPTION
			"Get configuration or firmware, then update it.
			 When update succeeded, system will reboot automatically."
		::= { swhUpdateFirmware 10 }

	swhUpdateState OBJECT-TYPE
		SYNTAX    DisplayString (SIZE (0..255))
		ACCESS    read-only
		STATUS    mandatory
		DESCRIPTION
			"Messages for getting/putting file, updating config/firmware."
		::= { swhUpdateFirmware 12 }


-- SystemUtility(6).BackupConfiguration(5)

	swhBackupNTPStatus OBJECT-TYPE
		SYNTAX    DisplayString (SIZE (0..255))
		ACCESS    read-only
		STATUS    mandatory
		DESCRIPTION
			"NTP Status."
		::= { swhAutoBackupConfiguration 14 }

	swhBackupAuto OBJECT-TYPE
		SYNTAX    INTEGER { disable(0), enable(1) }
		ACCESS    read-write
		STATUS    mandatory
		DESCRIPTION
			"Enable or disable auto backup.
			 In order for the Auto Backup function to work properly,
			 the NTP function must be enabled for the device to acquire local time information."
		::= { swhAutoBackupConfiguration 2 }

	swhBackupTime OBJECT-TYPE
		SYNTAX    INTEGER (0..23)
		ACCESS    read-write
		STATUS    mandatory
		DESCRIPTION
			"Backup time at which hour of a day."
		::= { swhAutoBackupConfiguration 3 }

	swhBackupProtocol OBJECT-TYPE
		SYNTAX    INTEGER { tftp(0), ftp(1) }
		ACCESS    read-write
		STATUS    mandatory
		DESCRIPTION
			"Backup file from tftp or ftp server."
		::= { swhAutoBackupConfiguration 4 }

	swhBackupFileType OBJECT-TYPE
		SYNTAX    INTEGER { configuration(1) }
		ACCESS    read-only
		STATUS    mandatory
		DESCRIPTION
			"Backup file type."
		::= { swhAutoBackupConfiguration 5 }

	swhBackupServerIPAddr OBJECT-TYPE
		SYNTAX    DisplayString (SIZE (0..255))
		ACCESS    read-write
		STATUS    mandatory
		DESCRIPTION
			"TFTP/FTP server ip address."
		::= { swhAutoBackupConfiguration 6 }

	swhBackupUserName OBJECT-TYPE
		SYNTAX    DisplayString (SIZE (0..255))
		ACCESS    read-write
		STATUS    mandatory
		DESCRIPTION
			"FTP server login user name."
		::= { swhAutoBackupConfiguration 7 }

	swhBackupPassword OBJECT-TYPE
		SYNTAX    DisplayString (SIZE (0..255))
		ACCESS    read-write
		STATUS    mandatory
		DESCRIPTION
			"FTP server login password."
		::= { swhAutoBackupConfiguration 8 }

	swhBackupFileDirectory OBJECT-TYPE
		SYNTAX    DisplayString (SIZE (0..255))
		ACCESS    read-write
		STATUS    mandatory
		DESCRIPTION
			"Backup file directory."
		::= { swhAutoBackupConfiguration 9 }

	swhBackupFileName OBJECT-TYPE
		SYNTAX    DisplayString (SIZE (0..255))
		ACCESS    read-only
		STATUS    mandatory
		DESCRIPTION
			"Backup file name."
		::= { swhAutoBackupConfiguration 10 }

	swhBackupState OBJECT-TYPE
		SYNTAX    DisplayString (SIZE (0..255))
		ACCESS    read-only
		STATUS    mandatory
		DESCRIPTION
			"Messages for backup."
		::= { swhAutoBackupConfiguration 12 }


-- SystemUtility(6).LoopBackTest(6)

--	swhDiagnosticPort OBJECT-TYPE
--		SYNTAX    INTEGER { select(0),
--		                    port01(1),
--		                    port02(2),
--		                    port03(3),
--		                    port04(4),
--		                    port05(5),
--		                    port06(6)
--		                    }
--		ACCESS    read-write
--		STATUS    mandatory
--		DESCRIPTION
--			"LoopBack Test Port"
--		::= { swhLoopbackTest 1 }

--	swhAccompanyPort OBJECT-TYPE
--		SYNTAX    INTEGER { select(0),
--		                    port01(1),
--		                    port02(2),
--		                    port03(3),
--		                    port04(4),
--		                    port05(5),
--		                    port06(6)
--		                    }
--		ACCESS    read-write
--		STATUS    mandatory
--		DESCRIPTION
--			"LoopBack Test swhAccompany Port"
--		::= { swhLoopbackTest 2 }

--	swhVlanID OBJECT-TYPE
--		SYNTAX    INTEGER (1..4094)
--		ACCESS    read-write
--		STATUS    mandatory
--		DESCRIPTION
--			"LoopBack Test VlanID"
--		::= { swhLoopbackTest 3 }

--	swhTestTime OBJECT-TYPE
--		SYNTAX    INTEGER (1..10)
--		ACCESS    read-write
--		STATUS    mandatory
--		DESCRIPTION
--			"LoopBack Test TestTime"
--		::= { swhLoopbackTest 4 }

--	swhState OBJECT-TYPE
--		SYNTAX    INTEGER { idle(0), active(1) }
--		ACCESS    read-only
--		STATUS    mandatory
--		DESCRIPTION
--			"LoopBack Test State"
--		::= { swhLoopbackTest 5 }

--	swhTimeRemaining OBJECT-TYPE
--		SYNTAX    DisplayString (SIZE (0..255))
--		ACCESS    read-only
--		STATUS    mandatory
--		DESCRIPTION
--			"LoopBack Test TimeRemaining"
--		::= { swhLoopbackTest 6 }

--	swhLoopbackStop
--		OBJECT IDENTIFIER ::= { swhLoopbackTest 7 }

--	swhStop OBJECT-TYPE
--		SYNTAX    INTEGER { stop(0) }
--		ACCESS    read-write
--		STATUS    mandatory
--		DESCRIPTION
--			"LoggingType's Terminal History ."
--		::= { swhLoopbackStop 1 }


-- SystemUtility(6).PortLinkFlapLog(9)

	swhPortLinkFlapLogPort OBJECT-TYPE
		SYNTAX    INTEGER { port01(0),
		                    port02(1),
		                    port03(2),
		                    port04(3),
		                    port05(4),
		                    port06(5)
		                  }
		ACCESS    read-write
		STATUS    mandatory
		DESCRIPTION
			"Per port search link flap log."
		::= { swhPortLinkFlapLog 1 }

	swhPortLinkFlapLogClear OBJECT-TYPE
		SYNTAX    INTEGER { normal(0), clear(1) }
		ACCESS    read-write
		STATUS    mandatory
		DESCRIPTION
			"Clear link flap log"
		::= { swhPortLinkFlapLog 2 }

	swhPortLinkFlapLogLocalTime OBJECT-TYPE
		SYNTAX    DisplayString (SIZE (0..255))
		ACCESS    read-only
		STATUS    mandatory
		DESCRIPTION
			"Local Time"
		::= { swhPortLinkFlapLog 3 }

	swhPortLinkFlapLogTotalPortFlaps OBJECT-TYPE
		SYNTAX    INTEGER (0..2147483647)
		ACCESS    read-only
		STATUS    mandatory
		DESCRIPTION
			"Total Port Flaps"
		::= { swhPortLinkFlapLog 4 }


-- SystemUtility(6).PortLinkFlapLog(9).PortLinkFlapLogTable(5)

	swhPortLinkFlapLogTable OBJECT-TYPE
		SYNTAX    SEQUENCE OF SwhPortLinkFlapLogEntry
		ACCESS    not-accessible
		STATUS    mandatory
		DESCRIPTION
			"Table of Port Link Flap Log."
		::= { swhPortLinkFlapLog 5 }

	-- Table Entry
	swhPortLinkFlapLogEntry OBJECT-TYPE
		SYNTAX    SwhPortLinkFlapLogEntry
		ACCESS    not-accessible
		STATUS    mandatory
		DESCRIPTION
			"An entry in the table, containing information
			about Port Link Flap Log"
		INDEX    { swhPortLinkFlapLogIndex }
		::= { swhPortLinkFlapLogTable 1 }

	SwhPortLinkFlapLogEntry ::=
		SEQUENCE {
			swhPortLinkFlapLogIndex
				INTEGER,
			swhPortLinkFlapLogNumber
				INTEGER,
			swhPortLinkFlapLogNTPTime
				DisplayString,
			swhPortLinkFlapLogUpTime
				DisplayString,
			swhPortLinkFlapLogPortStatus
				DisplayString,
			swhPortLinkFlapLogDescription
				DisplayString,
			swhPortLinkFlapLogWhenFlapped
				DisplayString,
			swhPortLinkFlapLogStatusDuration
				DisplayString,
			swhPortLinkFlapLogSFPRXPower
				DisplayString
		}

	swhPortLinkFlapLogIndex OBJECT-TYPE
		SYNTAX    INTEGER (0..2147483647)
		ACCESS    not-accessible
		STATUS    mandatory
		DESCRIPTION
			"A unique value for Link Flap Log index."
		::= { swhPortLinkFlapLogEntry 1 }

	swhPortLinkFlapLogNumber OBJECT-TYPE
		SYNTAX    INTEGER (0..2147483647)
		ACCESS    read-only
		STATUS    mandatory
		DESCRIPTION
			"A unique value for Link Flap Log index number."
		::= { swhPortLinkFlapLogEntry 2 }

	swhPortLinkFlapLogNTPTime OBJECT-TYPE
		SYNTAX    DisplayString
		ACCESS    read-only
		STATUS    mandatory
		DESCRIPTION
			"event happening time,
			 it is local time"
		::= { swhPortLinkFlapLogEntry 3 }

	swhPortLinkFlapLogUpTime OBJECT-TYPE
		SYNTAX    DisplayString
		ACCESS    read-only
		STATUS    mandatory
		DESCRIPTION
			"event happening time,
			it is system up time"
		::= { swhPortLinkFlapLogEntry 4 }

	swhPortLinkFlapLogPortStatus OBJECT-TYPE
		SYNTAX    DisplayString
		ACCESS    read-only
		STATUS    mandatory
		DESCRIPTION
			"event port status"
		::= { swhPortLinkFlapLogEntry 5 }

	swhPortLinkFlapLogDescription OBJECT-TYPE
		SYNTAX    DisplayString
		ACCESS    read-only
		STATUS    mandatory
		DESCRIPTION
			"event description"
		::= { swhPortLinkFlapLogEntry 6 }

	swhPortLinkFlapLogWhenFlapped OBJECT-TYPE
		SYNTAX    DisplayString
		ACCESS    read-only
		STATUS    mandatory
		DESCRIPTION
			"event when flapped"
		::= { swhPortLinkFlapLogEntry 7 }

	swhPortLinkFlapLogStatusDuration OBJECT-TYPE
		SYNTAX    DisplayString
		ACCESS    read-only
		STATUS    mandatory
		DESCRIPTION
			"event status duration"
		::= { swhPortLinkFlapLogEntry 8 }

	swhPortLinkFlapLogSFPRXPower OBJECT-TYPE
		SYNTAX    DisplayString
		ACCESS    read-only
		STATUS    mandatory
		DESCRIPTION
			"event SFP RX power(dBm)"
		::= { swhPortLinkFlapLogEntry 9 }

-- SystemUtility(6).LEDControl(11)

	swhLEDControlIntensity OBJECT-TYPE
		SYNTAX    INTEGER { high(0),
		                    medium(1),
		                    low(2),
							off(3)
		                  }
		ACCESS    read-write
		STATUS    mandatory
		DESCRIPTION
			"LED Light Control."
		::= { swhLEDControl 1 }

-- Traps(9)

	swhSystemPowerDown TRAP-TYPE
		ENTERPRISE    switchTraps
		--&ACTIONS    { critical }
		--&MESG       "System Power Down"
		DESCRIPTION
			"when system power down, send this trap."
		::=  1

	swhFaultAlarm TRAP-TYPE
		ENTERPRISE    switchTraps
		VARIABLES     { ifIndex, sysLocation }
		--&ACTIONS    { warning }
		--&MESG       "$2"
		DESCRIPTION   "when fault Alarm , send this trap."
		::=  8

	swhWarningAlarm TRAP-TYPE
		ENTERPRISE    switchTraps
		VARIABLES     { ifIndex, sysLocation }
		--&ACTIONS    { warning }
		--&MESG       "$2"
		DESCRIPTION   "when Warning Alarm , send this trap."
		::=  9

	swhMinorAlarm TRAP-TYPE
		ENTERPRISE    switchTraps
		VARIABLES     { ifIndex, sysLocation }
		--&ACTIONS    { minor }
		--&MESG       "$2"
		DESCRIPTION   "when Minor Alarm , send this trap."
		::=  10

	swhCriticalAlarm TRAP-TYPE
		ENTERPRISE    switchTraps
		VARIABLES     { ifIndex, sysLocation }
		--&ACTIONS    { critical }
		--&MESG       "$2"
		DESCRIPTION   "when Critical Alarm(Alert), send this trap."
		::=  12

	swhLoopBack TRAP-TYPE
		ENTERPRISE    switchTraps
		VARIABLES     { ifIndex, sysLocation }
		--&ACTIONS    { warning }
		--&MESG       "$2"
		DESCRIPTION   "when Loop back, send this trap."
		::=  13

	swhNormalAlarm TRAP-TYPE
		ENTERPRISE    switchTraps
		VARIABLES     { ifIndex, sysLocation }
		--&ACTIONS    { normal }
		--&MESG       "$2"
		DESCRIPTION   "when Normal Alarm(Information), send this trap."
		::=  16

--	swhCaseFanState TRAP-TYPE
--		ENTERPRISE    switchTraps
--		VARIABLES     { ifIndex, sysLocation }
--		
--		
--		DESCRIPTION   "fan state"
--		::=  19

	swhSystemPowerOn TRAP-TYPE
		ENTERPRISE    switchTraps
		VARIABLES     { ifIndex, sysLocation }
		--&ACTIONS    { critical }
		--&MESG       "$2"
		DESCRIPTION   "when system power up, send this trap."
		::=  20

	swhSystemPowerUp TRAP-TYPE
		ENTERPRISE    switchTraps
		--&ACTIONS    { normal }
		--&MESG       "System Power Up"
		DESCRIPTION
			"when system power up, send this trap."
		::=  21

	swhSystemUp TRAP-TYPE
		ENTERPRISE    switchTraps
		--&ACTIONS    { normal }
		--&MESG       "System Up"
		DESCRIPTION
			"when system up, send this trap."
		::=  25

END
