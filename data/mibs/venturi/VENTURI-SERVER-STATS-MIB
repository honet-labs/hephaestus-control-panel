VENTURI-SERVER-STATS-MIB DEFINITIONS ::= BEGIN

IMPORTS
    MODULE-IDENTITY,
    OBJECT-IDENTITY,
    OBJECT-TYPE,
    Counter32,
    Unsigned32,
    Counter64,
    Gauge32,
    Integer32,
    IpAddress,
    TimeTicks
        FROM SNMPv2-SMI
    DisplayString,
    TEXTUAL-CONVENTION
        FROM SNMPv2-TC
    vServerMgmt
        FROM VENTURI-SERVER-MIB
    VenturiProtocolType,
    VenturiSubscriberType,
    VenturiHexUnsigned32
        FROM VENTURI-TC
;


-- ------------------------------------------------------------------------
-- Module Identity
-- ------------------------------------------------------------------------
vServerStatistics MODULE-IDENTITY
    LAST-UPDATED    "201302220000Z"
    ORGANIZATION    "Venturi Wireless"
    CONTACT-INFO
       "Contact:  Customer Support

        Postal:   Venturi Wireless
                  490 North McCarthy Boulevard
                  Milpitas, CA  95035

        Phone:    408-215-5100
        FAX:      408-215-5105

        Web:      www.venturiwireless.com

        E-mail:   VenturiCustomerOps@venturiwireless.com"

    DESCRIPTION
        "Statistics poll-able from Venturi Servers

          Copyright 2004-2013 Venturi Wireless, Inc.
          All rights reserved.

          This MIB module defines the poll-able statistics available
          from a Venturi server. "

    REVISION    "201302220000Z"
        DESCRIPTION
            "1.10 - vServerClientInfoClientId and vServerClientInfoFsc changed
                    to DisplayString syntax and vServerClientInfoRowid made
                    readable."

    REVISION    "201301270000Z"
        DESCRIPTION
            "1.9 - vServerFscOverrideTable relocated to the
                   VENTURI-SERVER-SYSTEM-MIB and copyright updated
                   to 2013."

    REVISION    "201301210000Z"
        DESCRIPTION
            "1.8 - Added vServerClientInfoTable and vServerFscOverrideTable."

    REVISION    "201102080000Z"
        DESCRIPTION
            "1.7 - Added vServerAbbreviatedSubscriberClientTable"

    REVISION    "201101030000Z"
        DESCRIPTION 
            "1.6 - Updated copyright date to 2011"

    REVISION    "201009200000Z"
        DESCRIPTION
            "1.5 - Added vServerStatsPerfGraph"
    
    REVISION    "201001060000Z"
        DESCRIPTION 
            "1.4 - Updated copyright date to 2010"

    REVISION    "200804300000Z"
        DESCRIPTION
            "1.3 - Added detail to DESCRIPTION clauses."

    REVISION    "200802190000Z"
        DESCRIPTION
            "1.2 - Capacity Stats are added."
            
    REVISION    "200604270000Z"
        DESCRIPTION
            "Make vServerSubscriberClientlessTransportConnections
             an Integer32.  This was declared as a Counter32 when it is
             not a monotonically increasing value."

    REVISION    "200507220000Z"
        DESCRIPTION
            "1.1 - Add 

                     vServerTotalCompressorContexts 
                     vServerUsedCompressorContexts 

                   to vServerStatsSystemScalars."                 

    REVISION    "200502170000Z"
        DESCRIPTION
            "1.0 - Initial document."

    ::= { vServerMgmt 3 }

-- --------------------------------------------
--  Divisions within statistics
-- --------------------------------------------

vServerStatsSystem      OBJECT IDENTIFIER ::= { vServerStatistics 1 }
vServerStatsTraffic     OBJECT IDENTIFIER ::= { vServerStatistics 2 }
vServerStatsTransport   OBJECT IDENTIFIER ::= { vServerStatistics 3 }
vServerStatsSubscriber  OBJECT IDENTIFIER ::= { vServerStatistics 4 }
vServerStatsCapacity	OBJECT IDENTIFIER ::= { vServerStatistics 5 }
vServerStatsHealthcheck OBJECT IDENTIFIER ::= { vServerStatistics 6 }
vServerStatsPerfGraph   OBJECT IDENTIFIER ::= { vServerStatistics 7 }

-- --------------------------------------------
--  vServerStatsSystem
--  Description:
--    Defines the counters and gauges that may be used to
--    monitor the performance of the Venturi optimization server
-- --------------------------------------------

vServerStatsSystemScalars OBJECT IDENTIFIER ::= { vServerStatsSystem 1 }
vServerStatsSystemTables  OBJECT IDENTIFIER ::= { vServerStatsSystem 2 }

vServerSystemTotalVenturiBuffers OBJECT-TYPE
    SYNTAX        Integer32
    MAX-ACCESS    read-only
    STATUS        current
    DESCRIPTION
        "Total number of buffers in the server.  This is the number of
        buffers allocated at system initialization."
    ::= { vServerStatsSystemScalars 1 }

vServerStatsSystemUsedVenturiBuffers OBJECT-TYPE
    SYNTAX        Integer32
    MAX-ACCESS    read-only
    STATUS        current
    DESCRIPTION
        "The number of Venturi Buffers (VBufs) currently in use in the 
        server.  Venturi divides up most of free memory at initialization
        time into Venturi Buffers (VBufs).  VBufs are used for a variety
        of purposes, but primarily hold the data streams that pass through
        the server.  Because so much memory is allocated to VBufs, the
        memory utilization may look very high on a Venturi server, even
        under light load.  For this reason, it is better to look at the
        percentage of total VBufs in use rather than the total memory
        in use."

    ::= { vServerStatsSystemScalars 2 }

vServerTotalStreamContexts OBJECT-TYPE
    SYNTAX        Integer32
    MAX-ACCESS    read-only
    STATUS        current
    DESCRIPTION
        "Total number of Stream contexts allocated at system initialization.
        Stream contexts are used to keep track of client requests, such as 
        a request for a particular web page."
    ::= { vServerStatsSystemScalars 3 }

vServerUsedStreamContexts OBJECT-TYPE
    SYNTAX        Integer32
    MAX-ACCESS    read-only
    STATUS        current
    DESCRIPTION
        "Number of Stream Contexts currently in use."
    ::= { vServerStatsSystemScalars 4 }


vServerTotalCompressorContexts OBJECT-TYPE
    SYNTAX        Integer32
    MAX-ACCESS    read-only
    STATUS        current
    DESCRIPTION
        "Total number of Compressor Contexts allocated at system
        initialization.  These are data structures used to keep track
        of compression or decompression requests."
    ::= { vServerStatsSystemScalars 5 }

vServerUsedCompressorContexts OBJECT-TYPE
    SYNTAX        Integer32
    MAX-ACCESS    read-only
    STATUS        current
    DESCRIPTION
        "Number of Compressor Contexts currently in use."
    ::= { vServerStatsSystemScalars 6 }

vServerCompressorQueueDepthMax OBJECT-TYPE
    SYNTAX        Integer32
    MAX-ACCESS    read-only
    STATUS        current
    DESCRIPTION
        "The maximum number of buffers (VBufs) allowed to be 
        queued to compressors before triggering flow control.  
        The actual number of buffers queued may temporarily rise
        somewhat above this value."
    ::= { vServerStatsSystemScalars 7 }

vServerCompressorQueueDepth OBJECT-TYPE
    SYNTAX        Integer32
    MAX-ACCESS    read-only
    STATUS        current
    DESCRIPTION
        "Current number of buffers queued to compressors.
         This value may burst to high levels, but a 
         continuously high value indicates the server may
         be experiencing performance degradation due to
         operating beyond capacity."
    ::= { vServerStatsSystemScalars 8 }

vServerCpuUtilization OBJECT-TYPE
    SYNTAX        Gauge32
    MAX-ACCESS    read-only
    STATUS        current
    DESCRIPTION
        "The overall CPU utilization of the Venturi server 
         as a percent."
    ::= { vServerStatsSystemScalars 9 }

-- --------------------------------------------
--  vServerStatsTraffic
--  Description:
--    Defines the counters and gauges that provide data traffic 
--    classification per protocol.  
--   
--    Note: although this statistics are nominally indexed by
--          Virtual Venturi Server (VVS), currently only the
--          system totals are available (index 0).
-- --------------------------------------------

vServerStatsTrafficScalars OBJECT IDENTIFIER ::= { vServerStatsTraffic 1 }
vServerStatsTrafficTables  OBJECT IDENTIFIER ::= { vServerStatsTraffic 2 }

vServerByteCountReclassification OBJECT-TYPE
    SYNTAX        Counter64
    MAX-ACCESS    read-only
    STATUS        current
    DESCRIPTION
        "Total number of reclassifies due to byte count."
    ::= { vServerStatsTrafficScalars 1 }

vServerPeriodicClearReclassification OBJECT-TYPE
    SYNTAX        Counter64
    MAX-ACCESS    read-only
    STATUS        current
    DESCRIPTION
        "Total number of reclassifies due to periodic clear
         right now."
    ::= { vServerStatsTrafficScalars 2 }

vServerPeriodicClearBytes OBJECT-TYPE
    SYNTAX        Counter64
    MAX-ACCESS    read-only
    STATUS        current
    DESCRIPTION
        "Total number of bytes transfered on periodic clear."
    ::= { vServerStatsTrafficScalars 3 }

--
-- Traffic Table
--
vServerTrafficTable OBJECT-TYPE
    SYNTAX      SEQUENCE OF ServerTrafficEntry
    MAX-ACCESS  not-accessible
    STATUS      current
    DESCRIPTION
            "A table of traffic measures broken down by protocol.
            These counts are collected in the application layer
            and do not include UDP, VTP or TCP headers in the byte
            countes."
    ::= { vServerStatsTrafficTables 1 }

vServerTrafficEntry OBJECT-TYPE
    SYNTAX      ServerTrafficEntry
    MAX-ACCESS  not-accessible
    STATUS      current
    DESCRIPTION
            "An entry in the Venturi server traffic table.
            Indexed by the following
             - VVSId (VVSId = 0 represents the entire server)
             - protocol (protocol = ALL represents all protocols together)

            Note:  currently only the VVS index of 0 is available
            "
    INDEX       { vServerTrafficVVSId, vServerTrafficProtocolId }
    ::= { vServerTrafficTable 1 }

ServerTrafficEntry ::=
    SEQUENCE {
        vServerTrafficVVSId               Integer32,
        vServerTrafficProtocolId          Integer32,
        vServerTrafficVVSTag              OCTET STRING,
        vServerTrafficProtocolDescr       OCTET STRING,
        vServerTrafficFromExternal        Counter64,
        vServerTrafficToExternal          Counter64,
        vServerTrafficFromTransport       Counter64,
        vServerTrafficToTransport         Counter64,
        vServerTrafficFromClientless      Counter64,
        vServerTrafficToClientless        Counter64,
        vServerTrafficTotalStreamContexts Counter64,
        vServerTrafficCurStreamContexts   Counter64,
	vServerTrafficFromExternalCliented      Counter64,
        vServerTrafficToExternalCliented        Counter64,
        vServerTrafficFromExternalClientless    Counter64,
        vServerTrafficToExternalClientless      Counter64
    }

vServerTrafficVVSId OBJECT-TYPE
    SYNTAX        Integer32 (0..128)
    MAX-ACCESS    read-only
    STATUS        current
    DESCRIPTION
        "Represents the VVS ID of the row. If the value is 0,
        then it represents the entire server.  This number
        may range from 0 through vServerSystemMaxVVSId.
        
        Note:  currently only the index of 0 is available"
    ::= { vServerTrafficEntry 1 }

vServerTrafficProtocolId OBJECT-TYPE
    SYNTAX        Integer32 (0..32)
    MAX-ACCESS    read-only
    STATUS        current
    DESCRIPTION
        "A number associated with the protocol.  This is a loose
        association and may change if the Venturi server statistics
        gathering is reconfigured.  This field is offered to allow
        for indexing because the ProtocolDescr is an octet string
        which cannot be used for indexing.  This number indicates
        the row within VVSId which displays a particular protocol
        and will be consistent across all VVSId values."
    ::= { vServerTrafficEntry 2 }

vServerTrafficVVSTag OBJECT-TYPE
    SYNTAX        OCTET STRING
    MAX-ACCESS    read-only
    STATUS        current
    DESCRIPTION
        "An arbitrary string which may optionally be used to
        identify related Virtual Venturi Servers across a
        range of hardware servers.
        Note:  initially this string will be an ASCII
               representation of the VVS Id."
    ::= { vServerTrafficEntry 3 }


vServerTrafficProtocolDescr OBJECT-TYPE
    SYNTAX        OCTET STRING
    MAX-ACCESS    read-only
    STATUS        current
    DESCRIPTION
        "Printable name of the protocol for which the
         row's statistics apply.
         If the value is ALL, it represents all protocols together."
    ::= { vServerTrafficEntry 4 }

vServerTrafficFromExternal OBJECT-TYPE
    SYNTAX        Counter64
    MAX-ACCESS    read-only
    STATUS        current
    DESCRIPTION
        "Bytes transfered from external (i.e., not from a Venturi
         client.  For example, this would include bytes received
         from web servers."
    ::= { vServerTrafficEntry 5 }

vServerTrafficToExternal OBJECT-TYPE
    SYNTAX        Counter64
    MAX-ACCESS    read-only
    STATUS        current
    DESCRIPTION
        "Bytes transfered to external (i.e., not to a Venturi
         client.  For example, this would include bytes sent
         to web servers."
    ::= { vServerTrafficEntry 6 }

vServerTrafficFromTransport OBJECT-TYPE
    SYNTAX        Counter64
    MAX-ACCESS    read-only
    STATUS        current
    DESCRIPTION
        "Bytes sent from Venturi Transport to the compressors."
    ::= { vServerTrafficEntry 7 }

vServerTrafficToTransport OBJECT-TYPE
    SYNTAX        Counter64
    MAX-ACCESS    read-only
    STATUS        current
    DESCRIPTION
        "Bytes sent from compressors to Venturi Transport."
    ::= { vServerTrafficEntry 8 }

vServerTrafficFromClientless OBJECT-TYPE
    SYNTAX        Counter64
    MAX-ACCESS    read-only
    STATUS        current
    DESCRIPTION
        "Bytes transfered from a client-less browser connection."
    ::= { vServerTrafficEntry 9 }

vServerTrafficToClientless OBJECT-TYPE
    SYNTAX        Counter64
    MAX-ACCESS    read-only
    STATUS        current
    DESCRIPTION
        "Bytes transfered to a client-less browser connection."
    ::= { vServerTrafficEntry 10 }


vServerTrafficTotalStreamContexts OBJECT-TYPE
    SYNTAX        Counter64
    MAX-ACCESS    read-only
    STATUS        current
    DESCRIPTION
        "Total number of stream contexts that have been used to date."
    ::= { vServerTrafficEntry 11 }

vServerTrafficCurStreamContexts OBJECT-TYPE
    SYNTAX        Counter64
    MAX-ACCESS    read-only
    STATUS        current
    DESCRIPTION
        "Current active stream contexts."
    ::= { vServerTrafficEntry 12 }

vServerTrafficFromExternalCliented OBJECT-TYPE
    SYNTAX        Counter64
    MAX-ACCESS    read-only
    STATUS        current
    DESCRIPTION
        "Bytes transfered from external (i.e., not from a Venturi
         client) that accounts for the cliented traffic.  For example, 
         this would include bytes received from web servers."
    ::= { vServerTrafficEntry 13 }

vServerTrafficToExternalCliented OBJECT-TYPE
    SYNTAX        Counter64
    MAX-ACCESS    read-only
    STATUS        current
    DESCRIPTION
        "Bytes transfered to external (i.e., not to a Venturi
         client) that accounts for the cliented traffic.  For example, 
         this would include bytes sent to web servers."
    ::= { vServerTrafficEntry 14 }

vServerTrafficFromExternalClientless OBJECT-TYPE
    SYNTAX        Counter64
    MAX-ACCESS    read-only
    STATUS        current
    DESCRIPTION
        "Bytes transfered from external (i.e., not from a Venturi
         client) that accounts for the clientiless traffic.  For example, 
         this would include bytes received from web servers."
    ::= { vServerTrafficEntry 15 }

vServerTrafficToExternalClientless OBJECT-TYPE
    SYNTAX        Counter64
    MAX-ACCESS    read-only
    STATUS        current
    DESCRIPTION
        "Bytes transfered to external (i.e., not to a Venturi
         client) that accounts for the clientless traffic.  For example, 
         this would include bytes sent to web servers."
    ::= { vServerTrafficEntry 16 }

-- --------------------------------------------
--  vServerStatsTransport
--  Description:
--    Defines the counters and gauges that provide the performance of
--    Venturi Transport.
--    Provides information about Virtual Connections (VCs)
-- --------------------------------------------

vServerStatsTransportScalars OBJECT IDENTIFIER ::= { vServerStatsTransport 1 }
vServerStatsTransportTables  OBJECT IDENTIFIER ::= { vServerStatsTransport 2 }

vServerTransportTable OBJECT-TYPE
    SYNTAX      SEQUENCE OF ServerTransportEntry
    MAX-ACCESS  not-accessible
    STATUS      current
    DESCRIPTION
            "A table of traffic measures broken down by VVS and protocol."
    ::= { vServerStatsTransportTables 1 }

vServerTransportEntry OBJECT-TYPE
    SYNTAX      ServerTransportEntry
    MAX-ACCESS  not-accessible
    STATUS      current
    DESCRIPTION
            "An entry in the server traffic table.
            Indexed by the following
             - VVS (VVSId = 0 represents the entire server)
            "
    INDEX       { vServerTransportVVSId }
    ::= { vServerTransportTable 1 }

ServerTransportEntry ::=
    SEQUENCE {
        vServerTransportVVSId                    Integer32,
        vServerTransportVVSTag                   OCTET STRING,
        vServerTransportPacketsSent              Counter64,
        vServerTransportPacketsRecd              Counter64,
        vServerTransportPacketsRetransmitted     Counter64,
        vServerTransportBytesSent                Counter64,
        vServerTransportBytesRecd                Counter64,
        vServerTransportBytesRetransmitted       Counter64,
        vServerTransportUndeliverableToClients   Counter64,
        vServerTransportUndeliverableToComp      Counter64,
        vServerTransportTotalConnections         Counter64,
        vServerTransportFailedConnections        Counter64,
        vServerTransportCurrentConnections       Counter64, 
        vServerTransportBytesToComp              Counter64, 
        vServerTransportBytesFromComp            Counter64  
    }

vServerTransportVVSId OBJECT-TYPE
    SYNTAX        Integer32 (0..128)
    MAX-ACCESS    read-only
    STATUS        current
    DESCRIPTION
        "Represents the VVS ID of the row. If the value is 0,
        then it represents the entire server."
    ::= { vServerTransportEntry 1 }

vServerTransportVVSTag OBJECT-TYPE
    SYNTAX        OCTET STRING
    MAX-ACCESS    read-only
    STATUS        current
    DESCRIPTION
        "An arbitrary string which may optionally be used to
        identify related Virtual Venturi Servers across a
        range of hardware servers.
        Note:  initially this string will be an ASCII
               representation of the VVS Id."
    ::= { vServerTransportEntry 2 }

vServerTransportPacketsSent OBJECT-TYPE
    SYNTAX        Counter64
    MAX-ACCESS    read-only
    STATUS        current
    DESCRIPTION
        "Total number of packets sent to Venturi clients."
    ::= { vServerTransportEntry 3 }

vServerTransportPacketsRecd OBJECT-TYPE
    SYNTAX        Counter64
    MAX-ACCESS    read-only
    STATUS        current
    DESCRIPTION
        "Total number of packets received from Venturi clients."
    ::= { vServerTransportEntry 4 }

vServerTransportPacketsRetransmitted OBJECT-TYPE
    SYNTAX        Counter64
    MAX-ACCESS    read-only
    STATUS        current
    DESCRIPTION
        "Total number of packets retransmitted to Venturi clients."
    ::= { vServerTransportEntry 5 }

vServerTransportBytesSent OBJECT-TYPE
    SYNTAX        Counter64
    MAX-ACCESS    read-only
    STATUS        current
    DESCRIPTION
        "Total number of bytes sent to Venturi clients."
    ::= { vServerTransportEntry 6 }

vServerTransportBytesRecd OBJECT-TYPE
    SYNTAX        Counter64
    MAX-ACCESS    read-only
    STATUS        current
    DESCRIPTION
        "Total number of bytes received from Venturi clients."
    ::= { vServerTransportEntry 7 }

vServerTransportBytesRetransmitted OBJECT-TYPE
    SYNTAX        Counter64
    MAX-ACCESS    read-only
    STATUS        current
    DESCRIPTION
        "Total number of bytes retransmitted to Venturi clients."
    ::= { vServerTransportEntry 8 }

vServerTransportUndeliverableToClients OBJECT-TYPE
    SYNTAX        Counter64
    MAX-ACCESS    read-only
    STATUS        current
    DESCRIPTION
        "Total number of bytes undelivered to Venturi clients."
    ::= { vServerTransportEntry 9 }

vServerTransportUndeliverableToComp OBJECT-TYPE
    SYNTAX        Counter64
    MAX-ACCESS    read-only
    STATUS        current
    DESCRIPTION
        "Total number of bytes undelivered to compressor."
    ::= { vServerTransportEntry 10 }

vServerTransportTotalConnections OBJECT-TYPE
    SYNTAX        Counter64
    MAX-ACCESS    read-only
    STATUS        current
    DESCRIPTION
        "Total number of transport connections (VCs) completed by Venturi Clients."
    ::= { vServerTransportEntry 11 }

vServerTransportFailedConnections OBJECT-TYPE
    SYNTAX        Counter64
    MAX-ACCESS    read-only
    STATUS        current
    DESCRIPTION
        "Total number of transport connection failures."
    ::= { vServerTransportEntry 12 }

vServerTransportCurrentConnections OBJECT-TYPE
    SYNTAX        Counter64
    MAX-ACCESS    read-only
    STATUS        current
    DESCRIPTION
        "Total number of currently active transport connections (VCs)."
    ::= { vServerTransportEntry 13 }

vServerTransportBytesToComp OBJECT-TYPE
    SYNTAX        Counter64
    MAX-ACCESS    read-only
    STATUS        current
    DESCRIPTION
        "Total number of bytes sent to compressors."
    ::= { vServerTransportEntry 14 }

vServerTransportBytesFromComp OBJECT-TYPE
    SYNTAX        Counter64
    MAX-ACCESS    read-only
    STATUS        current
    DESCRIPTION
        "Total number of bytes received from compressors."
    ::= { vServerTransportEntry 15 }

-- --------------------------------------------
--  vServerStatsSubscriber
--  Description:
--    Provides information about subscribers (real connections)
-- --------------------------------------------

vServerStatsSubscriberScalars OBJECT IDENTIFIER ::= { vServerStatsSubscriber 1 }
vServerStatsSubscriberTables  OBJECT IDENTIFIER ::= { vServerStatsSubscriber 2 }

vServerClientLimitExceeded OBJECT-TYPE
    SYNTAX        Counter64
    MAX-ACCESS    read-only
    STATUS        current
    DESCRIPTION
        "Total number of times a subscriber running Venturi client
        was refused connection due to server limit.  If this count
        is constantly increasing, it may mean that client users
        are experiencing degraded service.  This is an indicator that
        more Venturi capicity is needed."
    ::= { vServerStatsSubscriberScalars 1 }

vServerClientlessLimitExceeded OBJECT-TYPE
    SYNTAX        Counter64
    MAX-ACCESS    read-only
    STATUS        current
    DESCRIPTION
        "Total number of times a client-less subscriber was refused
        connection due to server limit.  If Clientless access is 
        enabled and this value is increasing, more Venturi capacity
        is needed."
    ::= { vServerStatsSubscriberScalars 2 }

-- --------------------------------
-- Subscriber usage
-- --------------------------------
vServerSubscriberUsageTable OBJECT-TYPE
    SYNTAX      SEQUENCE OF ServerSubscriberUsageEntry
    MAX-ACCESS  not-accessible
    STATUS      current
    DESCRIPTION
            "A table of subscriber usage broken down by type (cliented
            and clientless), VVS and protocol."
    ::= { vServerStatsSubscriberTables 1 }

vServerSubscriberUsageEntry OBJECT-TYPE
    SYNTAX      ServerSubscriberUsageEntry
    MAX-ACCESS  not-accessible
    STATUS      current
    DESCRIPTION
            "An entry in the server traffic table.
            Indexed by the following
             - VVSId (VVSId = 0 represents the entire server)
             - type (type = Client | Clientless)
             - protocol (protocol = ALL represents all protocols together)
            "
    INDEX       { vServerSubscriberType,
                  vServerSubscriberVVSId }
    ::= { vServerSubscriberUsageTable 1 }

ServerSubscriberUsageEntry ::=
    SEQUENCE {
        vServerSubscriberType                   VenturiSubscriberType,
        vServerSubscriberVVSId                  Integer32,
        vServerSubscriberVVSTag                 OCTET STRING,
        vServerSubscriberTotalCount             Counter64,
        vServerSubscriberCurrCount              Gauge32,
        vServerSubscriberAuthenticationFailures Counter64,
        vServerSubscriberAbortedConnections     Counter64,
        vServerSubscriberReassignmentFailures   Counter64,
        vServerSubscriberStandbyCount           Counter64,
        vServerSubscriberInactiveCount          Counter64,
        vServerSubscriberReassignmentCount      Counter64,
        vServerSubscriberByteCount              Counter64
    }

vServerSubscriberType OBJECT-TYPE
    SYNTAX        VenturiSubscriberType
    MAX-ACCESS    read-only
    STATUS        current
    DESCRIPTION
        "A numberic value corresponding to the type of subscriber
        (client or clientless)."
    ::= { vServerSubscriberUsageEntry 1 }

vServerSubscriberVVSId OBJECT-TYPE
    SYNTAX        Integer32 (0..128)
    MAX-ACCESS    read-only
    STATUS        current
    DESCRIPTION
        "Represents the VVS ID of the row. If the value is 0,
        then it represents the entire server.  This number
        may range from 0 through vServerSystemMaxVVSId."
    ::= { vServerSubscriberUsageEntry 2 }

vServerSubscriberVVSTag OBJECT-TYPE
    SYNTAX        OCTET STRING
    MAX-ACCESS    read-only
    STATUS        current
    DESCRIPTION
        "An arbitrary string which may optionally be used to
        identify related Virtual Venturi Servers across a
        range of hardware servers.
        Note:  initially this string will be an ASCII
               representation of the VVS Id."
    ::= { vServerSubscriberUsageEntry 3 }

vServerSubscriberTotalCount OBJECT-TYPE
    SYNTAX        Counter64
    MAX-ACCESS    read-only
    STATUS        current
    DESCRIPTION
        "Total number of subscribers served by this server."
    ::= { vServerSubscriberUsageEntry 4 }

vServerSubscriberCurrCount OBJECT-TYPE
    SYNTAX        Gauge32
    MAX-ACCESS    read-only
    STATUS        current
    DESCRIPTION
        "Current number of active subscribers."
    ::= { vServerSubscriberUsageEntry 5 }

vServerSubscriberAuthenticationFailures OBJECT-TYPE
    SYNTAX        Counter64
    MAX-ACCESS    read-only
    STATUS        current
    DESCRIPTION
        "Total number of authentication failures observed since 
        last reboot."
    ::= { vServerSubscriberUsageEntry 6 }

vServerSubscriberAbortedConnections OBJECT-TYPE
    SYNTAX        Counter64
    MAX-ACCESS    read-only
    STATUS        current
    DESCRIPTION
        "Total number of connections dropped since last
         reboot because of lack of response from the other side."
    ::= { vServerSubscriberUsageEntry 7 }

vServerSubscriberReassignmentFailures OBJECT-TYPE
    SYNTAX        Counter64
    MAX-ACCESS    read-only
    STATUS        current
    DESCRIPTION
        "Total number of client connections which have been 
        rejected since last reboot for exceeding license."
    ::= { vServerSubscriberUsageEntry 8 }

vServerSubscriberStandbyCount OBJECT-TYPE
    SYNTAX        Counter64
    MAX-ACCESS    read-only
    STATUS        current
    DESCRIPTION
        "Current number of standby subscribers.
        A standby subscriber is one with no active VCs
        (virtual connections) and which has not generated
        activity in the last 5 minutes."
    ::= { vServerSubscriberUsageEntry 9 }

vServerSubscriberInactiveCount OBJECT-TYPE
    SYNTAX        Counter64
    MAX-ACCESS    read-only
    STATUS        current
    DESCRIPTION
        "Current number of idle subscribers. 
        An inactive subscriber is one with no active VCs
        (virtual connections) and which has not generated
        activity in the last hour."
    ::= { vServerSubscriberUsageEntry 10 }

vServerSubscriberReassignmentCount OBJECT-TYPE
    SYNTAX        Counter64
    MAX-ACCESS    read-only
    STATUS        current
    DESCRIPTION
        "Number of times subscribers have been re-assigned
        to a new entry in the RC table (represended by
        the vServerSubscriberClientTable in this MIB)."
    ::= { vServerSubscriberUsageEntry 11 }

vServerSubscriberByteCount OBJECT-TYPE
    SYNTAX        Counter64
    MAX-ACCESS    read-only
    STATUS        current
    DESCRIPTION
        "The number of bytes transmitted to and received
         from external sources (origin servers) on behalf
         of user connections."
    ::= { vServerSubscriberUsageEntry 12 }

-- --------------------------------
-- Active Client subscribers list
-- --------------------------------
vServerSubscriberClientTable OBJECT-TYPE
    SYNTAX      SEQUENCE OF ServerSubscriberClientEntry
    MAX-ACCESS  not-accessible
    STATUS      current
    DESCRIPTION
            "A table of active cliented subscriber connections."
    ::= { vServerStatsSubscriberTables 2 }

vServerSubscriberClientEntry OBJECT-TYPE
    SYNTAX      ServerSubscriberClientEntry
    MAX-ACCESS  not-accessible
    STATUS      current
    DESCRIPTION
            "An entry in the client table.
            "
    INDEX       { vServerSubscriberClientRowId }
    ::= { vServerSubscriberClientTable 1 }

ServerSubscriberClientEntry ::=
    SEQUENCE {
        vServerSubscriberClientRowId                Unsigned32,
        vServerSubscriberClientUniqueId             DisplayString,
        vServerSubscriberClientIPAddress            IpAddress,
        vServerSubscriberClientVersion              DisplayString,
        vServerSubscriberClientLastAccessTime       Integer32,
        vServerSubscriberClientTransportConnections Integer32,
        vServerSubscriberClientVVSTag               DisplayString,
        vServerSubscriberClientUserInfo             DisplayString,
        vServerSubscriberClientConnType             DisplayString,
        vServerSubscriberClientOS                   DisplayString,
        vServerSubscriberClientMAC                  DisplayString,
        vServerSubscriberClientPhone                DisplayString,
        vServerSubscriberClientConnDuration         TimeTicks,
        vServerSubscriberClientVTPPktsSent          Counter64,
        vServerSubscriberClientVTPPktsRcvd          Counter64,
        vServerSubscriberClientVTPBytesSent         Counter64,
        vServerSubscriberClientVTPBytesRcvd         Counter64,
        vServerSubscriberClientVTPDropPkts          Counter64,
        vServerSubscriberClientVTPReXmitPkts        Counter64,
        vServerSubscriberClientVTPErrorPkts         Counter64,
        vServerSubscriberClientVTPBWToClient        Counter32,
        vServerSubscriberClientVTPBWFromClient      Counter32,
        vServerSubscriberClientFromExternal         Counter64,
        vServerSubscriberClientToExternal           Counter64,
        vServerSubscriberClientFromTransport        Counter64,
        vServerSubscriberClientToTransport          Counter64,
        vServerSubscriberClientRTT                  Integer32,
        vServerSubscriberClientVTPReXmitBytes       Counter64
    }

vServerSubscriberClientRowId OBJECT-TYPE
    SYNTAX        Unsigned32
    MAX-ACCESS    not-accessible
    STATUS        current
    DESCRIPTION
        "The row number in this table."
    ::= { vServerSubscriberClientEntry 1 }

vServerSubscriberClientUniqueId OBJECT-TYPE
    SYNTAX        DisplayString
    MAX-ACCESS    read-only
    STATUS        current
    DESCRIPTION
        "ID that uniquely identifies this subscriber."
    ::= { vServerSubscriberClientEntry 2 }

vServerSubscriberClientIPAddress OBJECT-TYPE
    SYNTAX        IpAddress
    MAX-ACCESS    read-only
    STATUS        current
    DESCRIPTION
        "IP Address of the subscriber."
    ::= { vServerSubscriberClientEntry 3 }

vServerSubscriberClientVersion OBJECT-TYPE
    SYNTAX        DisplayString
    MAX-ACCESS    read-only
    STATUS        current
    DESCRIPTION
        "Version of Venturi Client that the subscriber is running."
    ::= { vServerSubscriberClientEntry 4 }

vServerSubscriberClientLastAccessTime OBJECT-TYPE
    SYNTAX        Integer32
    MAX-ACCESS    read-only
    STATUS        current
    DESCRIPTION
        "Time at which the connection was established in seconds 
         since epoch (midnight, Jan 1, 1970 GMT)."
    ::= { vServerSubscriberClientEntry 5 }

vServerSubscriberClientTransportConnections OBJECT-TYPE
    SYNTAX        Integer32
    MAX-ACCESS    read-only
    STATUS        current
    DESCRIPTION
        "Number of virtual connections currently active for 
        this subscriber."
    ::= { vServerSubscriberClientEntry 6 }


vServerSubscriberClientVVSTag OBJECT-TYPE
    SYNTAX        DisplayString
    MAX-ACCESS    read-only
    STATUS        current
    DESCRIPTION
        "An arbitrary string which may optionally be used to
        identify related Virtual Venturi Servers across a
        range of hardware servers.
        Note:  initially this string will be an ASCII
               representation of the VVS Id."
    ::= { vServerSubscriberClientEntry 7 }

vServerSubscriberClientUserInfo OBJECT-TYPE
    SYNTAX        DisplayString
    MAX-ACCESS    read-only
    STATUS        current
    DESCRIPTION
        "Client user information. This is only used in
        some models of Venturi optimization servers.
        Other models will simply return an empty string."
    ::= { vServerSubscriberClientEntry 8 }

vServerSubscriberClientConnType OBJECT-TYPE
    SYNTAX        DisplayString
    MAX-ACCESS    read-only
    STATUS        current
    DESCRIPTION
        "The connection type used by the client.  This information
         is only returned by Venturi client revision 4.0 and above.
         For earlier clients, this information is not available."
    ::= { vServerSubscriberClientEntry 9 }

vServerSubscriberClientOS OBJECT-TYPE
    SYNTAX        DisplayString
    MAX-ACCESS    read-only
    STATUS        current
    DESCRIPTION
        "The OS used on the client platform.  This information
         is only returned by Venturi client revision 4.0 and above.
         For earlier clients, this information is not available."
    ::= { vServerSubscriberClientEntry 10 }

vServerSubscriberClientMAC OBJECT-TYPE
    SYNTAX        DisplayString
    MAX-ACCESS    read-only
    STATUS        current
    DESCRIPTION
        "The MAC address of the interface used on the client for
         connection to the Venturi server.  This information
         is only returned by Venturi client revision 4.0 and above.
         For earlier clients, this information is not available."
    ::= { vServerSubscriberClientEntry 11 }

vServerSubscriberClientPhone OBJECT-TYPE
    SYNTAX        DisplayString
    MAX-ACCESS    read-only
    STATUS        current
    DESCRIPTION
        "If the client is using a dial-up connection, this is the
         phone number of the client interface.  For clients not using
         dial up, this field will be blank.  This information
         is only returned by Venturi client revision 4.0 and above.
         For earlier clients, this information is not available."
    ::= { vServerSubscriberClientEntry 12 }

vServerSubscriberClientConnDuration         OBJECT-TYPE
    SYNTAX        TimeTicks
    MAX-ACCESS    read-only
    STATUS        current
    DESCRIPTION
        "Duration of the current connection.  Units are hundredths
         of seconds."
    ::= { vServerSubscriberClientEntry 13 }

vServerSubscriberClientVTPPktsSent          OBJECT-TYPE
    SYNTAX        Counter64
    MAX-ACCESS    read-only
    STATUS        current
    DESCRIPTION
        "Number of VTP packets transmitted to the client."
    ::= { vServerSubscriberClientEntry 14 }

vServerSubscriberClientVTPPktsRcvd          OBJECT-TYPE
    SYNTAX        Counter64
    MAX-ACCESS    read-only
    STATUS        current
    DESCRIPTION
        "Number of VTP packets received from client."
    ::= { vServerSubscriberClientEntry 15 }

vServerSubscriberClientVTPBytesSent         OBJECT-TYPE
    SYNTAX        Counter64
    MAX-ACCESS    read-only
    STATUS        current
    DESCRIPTION
        "Number of bytes transmitted to the client over this
         VTP connection.  This value does not include UDP
         headers."
    ::= { vServerSubscriberClientEntry 16 }

vServerSubscriberClientVTPBytesRcvd         OBJECT-TYPE
    SYNTAX        Counter64
    MAX-ACCESS    read-only
    STATUS        current
    DESCRIPTION
        "Number of bytes received from the client over this
         VTP connection.  This value does not include UDP
         headers."
    ::= { vServerSubscriberClientEntry 17 }

vServerSubscriberClientVTPDropPkts          OBJECT-TYPE
    SYNTAX        Counter64
    MAX-ACCESS    read-only
    STATUS        current
    DESCRIPTION
        "Number of dropped packets."
    ::= { vServerSubscriberClientEntry 18 }

vServerSubscriberClientVTPReXmitPkts        OBJECT-TYPE
    SYNTAX        Counter64
    MAX-ACCESS    read-only
    STATUS        current
    DESCRIPTION
        "Number of transmitted packets."
    ::= { vServerSubscriberClientEntry 19 }

vServerSubscriberClientVTPErrorPkts         OBJECT-TYPE
    SYNTAX        Counter64
    MAX-ACCESS    read-only
    STATUS        current
    DESCRIPTION
        "Number of error packets."
    ::= { vServerSubscriberClientEntry 20 }

vServerSubscriberClientVTPBWToClient        OBJECT-TYPE
    SYNTAX        Counter32
    MAX-ACCESS    read-only
    STATUS        current
    DESCRIPTION
        "The most recent measure taken by transport of the bandwidth
         to the client in bits/second."
    ::= { vServerSubscriberClientEntry 21 }

vServerSubscriberClientVTPBWFromClient      OBJECT-TYPE
    SYNTAX        Counter32
    MAX-ACCESS    read-only
    STATUS        current
    DESCRIPTION
        "The most recent measure taken by transport of the bandwidth
         from the client in bits/second."
    ::= { vServerSubscriberClientEntry 22 }

vServerSubscriberClientFromExternal         OBJECT-TYPE
    SYNTAX        Counter64
    MAX-ACCESS    read-only
    STATUS        current
    DESCRIPTION
        "Bytes transfered from external (i.e., not from a Venturi
         client.  For example, this would include pages received
         from web servers.  This is the portion of the traffic
         described in vServerTrafficFromExternal attributable to
         this client.  This value does not include TCP headers."
    ::= { vServerSubscriberClientEntry 23 }

vServerSubscriberClientToExternal            OBJECT-TYPE
    SYNTAX        Counter64
    MAX-ACCESS    read-only
    STATUS        current
    DESCRIPTION
        "Bytes transfered to external (i.e., not to a Venturi
         client.  For example, this would include requests sent
         to web servers.  This is the portion of the traffic
         described in vServerTrafficToExternal attributable to
         this client.  This value does not include TCP headers."
    ::= { vServerSubscriberClientEntry 24 }

vServerSubscriberClientFromTransport        OBJECT-TYPE
    SYNTAX        Counter64
    MAX-ACCESS    read-only
    STATUS        current
    DESCRIPTION
        "Bytes received from the client through Transport.
         This is vServerSubscriberClientVTPBytesRcvd minus the VTP
         overhead.  It is the portion of the traffic described in 
         vServerTrafficToTransport attributable to this client."
    ::= { vServerSubscriberClientEntry 25 }

vServerSubscriberClientToTransport          OBJECT-TYPE
    SYNTAX        Counter64
    MAX-ACCESS    read-only
    STATUS        current
    DESCRIPTION
        "Bytes sent to Transport for transmission to the client.
         This is vServerSubscriberClientVTPBytesSent minus the VTP
         overhead.  It is the portion of the traffic described in  
         vServerTrafficFromTransport attributable to this client."
    ::= { vServerSubscriberClientEntry 26 }

vServerSubscriberClientRTT OBJECT-TYPE
    SYNTAX        Integer32 (0..65535)
    UNITS         "milliseconds"
    MAX-ACCESS    read-only
    STATUS        current
    DESCRIPTION
        "Measured round trip time between Venturi client and server."
    ::= { vServerSubscriberClientEntry 27 }
        
vServerSubscriberClientVTPReXmitBytes   OBJECT-TYPE
    SYNTAX        Counter64
    MAX-ACCESS    read-only
    STATUS        current
    DESCRIPTION
        "Bytes sent to Transport for retransmissions to the client."
    ::= { vServerSubscriberClientEntry 28 }

-- --------------------------------
-- Active Clientless subscribers list
-- --------------------------------
vServerSubscriberClientlessTable OBJECT-TYPE
    SYNTAX      SEQUENCE OF ServerSubscriberClientlessEntry
    MAX-ACCESS  not-accessible
    STATUS      current
    DESCRIPTION
            "A table of active client-less subscribers."
    ::= { vServerStatsSubscriberTables 3 }

vServerSubscriberClientlessEntry OBJECT-TYPE
    SYNTAX      ServerSubscriberClientlessEntry
    MAX-ACCESS  not-accessible
    STATUS      current
    DESCRIPTION
            "An entry in the client-less table.
            "
    INDEX       { vServerSubscriberClientlessRowId }
    ::= { vServerSubscriberClientlessTable 1 }

ServerSubscriberClientlessEntry ::=
    SEQUENCE {
        vServerSubscriberClientlessRowId                Unsigned32,
        vServerSubscriberClientlessIPAddress            IpAddress,
        vServerSubscriberClientlessLastAccessTime       Integer32,
        vServerSubscriberClientlessTransportConnections Integer32,
        vServerSubscriberClientlessVVSTag               DisplayString
    }

vServerSubscriberClientlessRowId OBJECT-TYPE
    SYNTAX        Unsigned32
    MAX-ACCESS    not-accessible
    STATUS        current
    DESCRIPTION
        "The row number in this table."
    ::= { vServerSubscriberClientlessEntry 1 }

vServerSubscriberClientlessIPAddress OBJECT-TYPE
    SYNTAX        IpAddress
    MAX-ACCESS    read-only
    STATUS        current
    DESCRIPTION
        "IP Address of the subscriber."
    ::= { vServerSubscriberClientlessEntry 2 }

vServerSubscriberClientlessLastAccessTime OBJECT-TYPE
    SYNTAX        Integer32
    MAX-ACCESS    read-only
    STATUS        current
    DESCRIPTION
        "Time at which the last activity was seen 
        for this subscriber, in seconds since epoch 
        (midnight, Jan 1, 1970 GMT)."
    ::= { vServerSubscriberClientlessEntry 3 }

vServerSubscriberClientlessTransportConnections OBJECT-TYPE
    SYNTAX        Integer32
    MAX-ACCESS    read-only
    STATUS        current
    DESCRIPTION
        "Number of virtual connections (VCs) currently active 
        for this subscriber."
    ::= { vServerSubscriberClientlessEntry 4 }


vServerSubscriberClientlessVVSTag OBJECT-TYPE
    SYNTAX        DisplayString
    MAX-ACCESS    read-only
    STATUS        current
    DESCRIPTION
        "An arbitrary string which may optionally be used to
        identify related Virtual Venturi Servers across a
        range of hardware servers.
        Note:  initially this string will be an ASCII
               representation of the VVS Id."
    ::= { vServerSubscriberClientlessEntry 5 }

-- --------------------------------
-- Abbreviated Active Clientless subscribers list
-- --------------------------------

vServerAbbreviatedSubscriberClientTable OBJECT-TYPE
    SYNTAX      SEQUENCE OF ServerAbbreviatedSubscriberClientEntry
    MAX-ACCESS  not-accessible
    STATUS      current
    DESCRIPTION
            "A table of abbreviated active cliented
             subscriber connections."
    ::= { vServerStatsSubscriberTables 4 }

vServerAbbreviatedSubscriberClientEntry OBJECT-TYPE
    SYNTAX      ServerAbbreviatedSubscriberClientEntry
    MAX-ACCESS  not-accessible
    STATUS      current
    DESCRIPTION
            "An entry in the abbreviated client stats table.
            "
    INDEX       { vServerAbbreviatedSubscriberClientRowId }
    ::= { vServerAbbreviatedSubscriberClientTable 1 }

ServerAbbreviatedSubscriberClientEntry ::=
    SEQUENCE {
        vServerAbbreviatedSubscriberClientRowId                Unsigned32,
        vServerAbbreviatedSubscriberClientIPAddress            IpAddress,
        vServerAbbreviatedSubscriberClientVTPBWToClient        Unsigned32,
        vServerAbbreviatedSubscriberClientVTPBWFromClient      Unsigned32,
        vServerAbbreviatedSubscriberClientRTT                  Unsigned32
    }

vServerAbbreviatedSubscriberClientRowId OBJECT-TYPE
    SYNTAX        Unsigned32
    MAX-ACCESS    not-accessible
    STATUS        current
    DESCRIPTION
        "The row number in this table."
    ::= { vServerAbbreviatedSubscriberClientEntry 1 }

vServerAbbreviatedSubscriberClientIPAddress OBJECT-TYPE
    SYNTAX        IpAddress
    MAX-ACCESS    read-only
    STATUS        current
    DESCRIPTION
        "IP Address of the subscriber."
    ::= { vServerAbbreviatedSubscriberClientEntry 2 }

vServerAbbreviatedSubscriberClientVTPBWToClient        OBJECT-TYPE
    SYNTAX        Unsigned32
    MAX-ACCESS    read-only
    STATUS        current
    DESCRIPTION
        "The most recent measure taken by transport of the bandwidth
         to the client in bits/second."
    ::= { vServerAbbreviatedSubscriberClientEntry 3 }

vServerAbbreviatedSubscriberClientVTPBWFromClient      OBJECT-TYPE
    SYNTAX        Unsigned32
    MAX-ACCESS    read-only
    STATUS        current
    DESCRIPTION
        "The most recent measure taken by transport of the bandwidth
         from the client in bits/second."
    ::= { vServerAbbreviatedSubscriberClientEntry 4 }

vServerAbbreviatedSubscriberClientRTT OBJECT-TYPE
    SYNTAX        Unsigned32 (0..65535)
    UNITS         "milliseconds"
    MAX-ACCESS    read-only
    STATUS        current
    DESCRIPTION
        "Measured round trip time between Venturi client and server."
    ::= { vServerAbbreviatedSubscriberClientEntry 5 }


-- --------------------------------
-- vServerClientInfoTable
-- --------------------------------

vServerClientInfoTable OBJECT-TYPE
    SYNTAX      SEQUENCE OF VServerClientInfoEntry
    MAX-ACCESS  not-accessible
    STATUS      current
    DESCRIPTION
            "Client information table."
    ::= { vServerStatsSubscriberTables 5 }

vServerClientInfoEntry OBJECT-TYPE
    SYNTAX      VServerClientInfoEntry
    MAX-ACCESS  not-accessible
    STATUS      current
    DESCRIPTION
            "An entry in the Client Info table
            "
    INDEX       { vServerClientInfoRowId }
    ::= { vServerClientInfoTable 1 }

VServerClientInfoEntry ::=
    SEQUENCE {
        vServerClientInfoRowId                Unsigned32,
        vServerClientInfoClientId             DisplayString,
        vServerClientInfoRemoteIp             IpAddress,
        vServerClientInfoSubIp                IpAddress,
        vServerClientInfoActVC                Counter64,
        vServerClientInfoBytesSent            Counter64,
        vServerClientInfoBytesRcvd            Counter64,
        vServerClientInfoXmitRate             Counter64,
        vServerClientInfoRecvRate             Counter64,
        vServerClientInfoRTT                  Counter64,
        vServerClientInfoNSub                 Counter64,
        vServerClientInfoFsc                  OCTET STRING,
        vServerClientInfoScale0               OCTET STRING,
        vServerClientInfoScale1               OCTET STRING,
        vServerClientInfoScale2               OCTET STRING,
        vServerClientInfoScale3               OCTET STRING
    }
        
vServerClientInfoRowId OBJECT-TYPE
    SYNTAX        Unsigned32
    MAX-ACCESS    read-only
    STATUS        current
    DESCRIPTION
        "The row number in this table."
    ::= { vServerClientInfoEntry 1 }

vServerClientInfoClientId OBJECT-TYPE
    SYNTAX        DisplayString
    MAX-ACCESS    read-only
    STATUS        current
    DESCRIPTION
        "Client identifier."
    ::= { vServerClientInfoEntry 2 }

vServerClientInfoRemoteIp OBJECT-TYPE
    SYNTAX        IpAddress
    MAX-ACCESS    read-only
    STATUS        current
    DESCRIPTION
        "IP address of the client."
    ::= { vServerClientInfoEntry 3 }

vServerClientInfoSubIp OBJECT-TYPE
    SYNTAX        IpAddress
    MAX-ACCESS    read-only
    STATUS        current
    DESCRIPTION
        "Subscriber address tied to this entry."
    ::= { vServerClientInfoEntry 4 }

vServerClientInfoActVC OBJECT-TYPE
    SYNTAX        Counter64
    MAX-ACCESS    read-only
    STATUS        current
    DESCRIPTION
        "Count of active virtual connections for this client."
    ::= { vServerClientInfoEntry 5 }

vServerClientInfoBytesSent OBJECT-TYPE
    SYNTAX        Counter64
    MAX-ACCESS    read-only
    STATUS        current
    DESCRIPTION
        "The number of bytes that have been sent."
    ::= { vServerClientInfoEntry 6 }

vServerClientInfoBytesRcvd OBJECT-TYPE
    SYNTAX        Counter64
    MAX-ACCESS    read-only
    STATUS        current
    DESCRIPTION
        "The number of bytes that have been received."
    ::= { vServerClientInfoEntry 7 }

vServerClientInfoXmitRate OBJECT-TYPE
    SYNTAX        Counter64
    MAX-ACCESS    read-only
    STATUS        current
    DESCRIPTION
        "Transmit rate."
    ::= { vServerClientInfoEntry 8 }

vServerClientInfoRecvRate OBJECT-TYPE
    SYNTAX        Counter64
    MAX-ACCESS    read-only
    STATUS        current
    DESCRIPTION
        "Receive rate."
    ::= { vServerClientInfoEntry 9 }

vServerClientInfoRTT OBJECT-TYPE
    SYNTAX        Counter64
    MAX-ACCESS    read-only
    STATUS        current
    DESCRIPTION
        "Round trip time"
    ::= { vServerClientInfoEntry 10 }

vServerClientInfoNSub OBJECT-TYPE
    SYNTAX        Counter64
    MAX-ACCESS    read-only
    STATUS        current
    DESCRIPTION
        ""
    ::= { vServerClientInfoEntry 11 }

vServerClientInfoFsc OBJECT-TYPE
    SYNTAX        OCTET STRING
    MAX-ACCESS    read-only
    STATUS        current
    DESCRIPTION
        ""
    ::= { vServerClientInfoEntry 12 }

vServerClientInfoScale0 OBJECT-TYPE
    SYNTAX        OCTET STRING
    MAX-ACCESS    read-only
    STATUS        current
    DESCRIPTION
        "Value of shaping class 0."
    ::= { vServerClientInfoEntry 13 }

vServerClientInfoScale1 OBJECT-TYPE
    SYNTAX        OCTET STRING
    MAX-ACCESS    read-only
    STATUS        current
    DESCRIPTION
        "Value of shaping class 1."
    ::= { vServerClientInfoEntry 14 }

vServerClientInfoScale2 OBJECT-TYPE
    SYNTAX        OCTET STRING
    MAX-ACCESS    read-only
    STATUS        current
    DESCRIPTION
        "Value of shaping class 2."
    ::= { vServerClientInfoEntry 15 }

vServerClientInfoScale3 OBJECT-TYPE
    SYNTAX        OCTET STRING
    MAX-ACCESS    read-only
    STATUS        current
    DESCRIPTION
        ""
    ::= { vServerClientInfoEntry 16 }


-- --------------------------------------------
--  vServerStatsCapacity
--  Description:
--    Provides information about capacity.
-- --------------------------------------------

vServerStatsCapacityScalars OBJECT IDENTIFIER 	::= { vServerStatsCapacity 1 }
vServerStatsCapacityTables  OBJECT IDENTIFIER 	::= { vServerStatsCapacity 2 }

vServerCapacityPeakPeriod OBJECT-TYPE
    SYNTAX        Integer32
    MAX-ACCESS    read-only
    STATUS        current
    DESCRIPTION
        "The peak interval used for averaging the overload."
    ::= { vServerStatsCapacityScalars 1 }

vServerCapacityLoad OBJECT-TYPE
    SYNTAX        Counter64
    MAX-ACCESS    read-only
    STATUS        current
    DESCRIPTION
        "The value of average overload. which is currently 
         TCPINOUT_30SECPEAK, VTPINTCPOUT_30SECPEAK or TCPINOUT_5MINAVG.
         Default is TCPINOUT_30SECPEAK"
    ::= { vServerStatsCapacityScalars 2 }


-- --------------------------------------------
--  vServerStatsHealthcheck
--  Description:
--    Provides information about system health.
-- --------------------------------------------

vServerStatsHealthcheckScalars OBJECT IDENTIFIER 	::= { vServerStatsHealthcheck 1 }
vServerStatsHealthcheckTables  OBJECT IDENTIFIER 	::= { vServerStatsHealthcheck 2 }

-- --------------------------------------------
--  vServerStatsHealthcheckScalarsClientless
--  Description:
--    Provides information about system health.
-- --------------------------------------------

vServerStatsHealthcheckClientless OBJECT IDENTIFIER 	::= { vServerStatsHealthcheckScalars 1 }
vServerStatsHealthcheckCliented   OBJECT IDENTIFIER 	::= { vServerStatsHealthcheckScalars 2 }

vServerHealthcheckClientlessRate OBJECT-TYPE
    SYNTAX        Gauge32
    MAX-ACCESS    read-only
    STATUS        current
    DESCRIPTION
        "Clientless Load, 0-100, 100 == overloaded"
    ::= { vServerStatsHealthcheckClientless 1 }

vServerHealthcheckClientlessFlow OBJECT-TYPE
    SYNTAX        Gauge32
    MAX-ACCESS    read-only
    STATUS        current
    DESCRIPTION
        "Clientless Health, 1 = healthy, 5 = overloaded"
    ::= { vServerStatsHealthcheckClientless 2 }

vServerHealthcheckClientedRate OBJECT-TYPE
    SYNTAX        Gauge32
    MAX-ACCESS    read-only
    STATUS        current
    DESCRIPTION
        "Cliented Load, 0-100, 100 == overloaded"
    ::= { vServerStatsHealthcheckCliented 1 }

-- --------------------------------------------
--  vServerStatsPerfGraph
--  Description:
--    Defines the counters and gauges that provide byte counts
--    required for generating performance graph.
-- --------------------------------------------

vServerStatsPerfGraphScalars OBJECT IDENTIFIER ::= { vServerStatsPerfGraph 1 }
vServerStatsPerfGraphTables  OBJECT IDENTIFIER ::= { vServerStatsPerfGraph 2 }

vServerStatsDirectInBytes OBJECT-TYPE
    SYNTAX        Counter64
    MAX-ACCESS    read-only
    STATUS        current
    DESCRIPTION
        "Total bytes received directly from external."
    ::= { vServerStatsPerfGraphScalars 1 }

vServerStatsProxyInBytes OBJECT-TYPE
    SYNTAX        Counter64
    MAX-ACCESS    read-only
    STATUS        current
    DESCRIPTION
        "Total bytes received from proxies."
    ::= { vServerStatsPerfGraphScalars 2 }

vServerStatsUncompressedCacheInBytes OBJECT-TYPE
    SYNTAX        Counter64
    MAX-ACCESS    read-only
    STATUS        current
    DESCRIPTION
        "Total uncompressed bytes from cache."
    ::= { vServerStatsPerfGraphScalars 3 }

vServerStatsSubscriberOutBytes OBJECT-TYPE
    SYNTAX        Counter64
    MAX-ACCESS    read-only
    STATUS        current
    DESCRIPTION
        "Total bytes sent to subscriber."
    ::= { vServerStatsPerfGraphScalars 4 }

END
