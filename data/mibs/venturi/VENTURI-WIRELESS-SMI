VENTURI-WIRELESS-SMI DEFINITIONS ::= BEGIN

IMPORTS
        MODULE-IDENTITY,
        OBJECT-IDENTITY,
        enterprises
                FROM SNMPv2-SMI;

-- ------------------------------------------------------------------------
-- Module Identity
-- ------------------------------------------------------------------------
venturiWireless MODULE-IDENTITY
    LAST-UPDATED    "201101030000Z"
    ORGANIZATION    "Venturi Wireless"
    CONTACT-INFO
       "Contact:  Customer Support

        Postal:   Venturi Wireless
                  490 North McCarthy Boulevard
                  Milpitas, CA  95035

        Phone:    408-215-5100
        FAX:      408-215-5105

        Web:      www.venturiwireless.com

        E-mail:   VenturiCustomerOps@venturiwireless.com"

    DESCRIPTION
        "The root MIB module for Venturi Wireless

          Copyright 2004-2011 Venturi Wireless
          All rights reserved.

          This MIB module specifies the overall structure of 
          Venturi Wireless SNMP accessible management information."

    REVISION    "201101030000Z"
        DESCRIPTION 
            "1.2 - Updated copyright date to 2011"

    REVISION    "201001060000Z"
        DESCRIPTION 
            "1.1 - Update copyright date to 2010"


    REVISION    "200502170000Z"
        DESCRIPTION
            "1.0 - Initial document."

    ::= { enterprises 3382 }



-- -----------------------------------------------------------------
-- Historic Information
-- -----------------------------------------------------------------
--    venturi.1  :  This is where the original Venturi release 1 MIB
--                    was defined.
--    venturi.2  :  This is where the original Venturi release 2 MIB
--                    was defined.


-- -----------------------------------------------------------------
-- Venturi Wireless Products definitions
-- -----------------------------------------------------------------
venturiProducts OBJECT-IDENTITY
        STATUS	current
        DESCRIPTION
                "venturiProducts is the root OBJECT IDENTIFIER from
                 which product categories are assigned. Each product 
                 category will define the sysObjectID for its product 
                 line."
        ::= { venturiWireless 11 }

venturiMgmt OBJECT-IDENTITY
        STATUS	current
        DESCRIPTION
                "venturiMgmt is the root OBJECT IDENTIFIER from
                 which product specific MIBS are defined."
        ::= { venturiWireless 12 }


END
