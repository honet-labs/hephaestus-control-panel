--
-- WIS-MIB.my
-- MIB generated by MG-SOFT Visual MIB Builder Version 5.0  Build 250
-- Monday, December 16, 2024 at 20:00:09
--

	WIS-MIB DEFINITIONS ::= BEGIN
 
		IMPORTS
			OBJECT-GROUP, MODULE-COMPLIANCE			
				FROM SNMPv2-CONF			
			enterprises, Integer32, OBJECT-TYPE, MODULE-IDENTITY			
				FROM SNMPv2-SMI			
			DisplayString			
				FROM SNMPv2-TC;
	
	
		wisMIB MODULE-IDENTITY 
			LAST-UPDATED "202412160000Z"		-- December 16, 2024 at 20:00:09
			ORGANIZATION 
				"WIS, Inc."
			CONTACT-INFO 
				"support@ui.com"
			DESCRIPTION 
				"The MIB module for WIS, Inc. entities"
			REVISION "202412160000Z"		-- December 16, 2024 at 20:00:09
			DESCRIPTION 
				"Split revision"
			::= { wis 1 }

		
	
	
--
-- Node definitions
--
	
		wis OBJECT IDENTIFIER ::= { enterprises 62821 }

		
		wisORTable OBJECT-TYPE
			SYNTAX SEQUENCE OF WisOREntry
			MAX-ACCESS not-accessible
			STATUS current
			DESCRIPTION
				"Capabilities"
			::= { wisMIB 1 }

		
		wisOREntry OBJECT-TYPE
			SYNTAX WisOREntry
			MAX-ACCESS not-accessible
			STATUS current
			DESCRIPTION
				"An entry in the wisORTable"
			INDEX { wisORIndex }
			::= { wisORTable 1 }

		
		WisOREntry ::=
			SEQUENCE { 
				wisORIndex
					Integer32,
				wisORID
					OBJECT IDENTIFIER,
				wisORDescr
					DisplayString
			 }

		wisORIndex OBJECT-TYPE
			SYNTAX Integer32 (1..255)
			MAX-ACCESS not-accessible
			STATUS current
			DESCRIPTION
				"Index for the wisORTable"
			::= { wisOREntry 1 }

		
		wisORID OBJECT-TYPE
			SYNTAX OBJECT IDENTIFIER
			MAX-ACCESS read-only
			STATUS current
			DESCRIPTION
				"OR ID"
			::= { wisOREntry 2 }

		
		wisORDescr OBJECT-TYPE
			SYNTAX DisplayString
			MAX-ACCESS read-only
			STATUS current
			DESCRIPTION
				"Description of idenfifier"
			::= { wisOREntry 3 }

		
		wisSnmpInfo OBJECT IDENTIFIER ::= { wisMIB 2 }

		
		wisSnmpGroups OBJECT IDENTIFIER ::= { wisSnmpInfo 1 }

		
		wisORInfoGroup OBJECT-GROUP
			OBJECTS { wisORID, wisORDescr }
			STATUS current
			DESCRIPTION 
				"Collection of related objects"
			::= { wisSnmpGroups 1 }

		
		wisORCompliance MODULE-COMPLIANCE
			STATUS current
			DESCRIPTION 
				"The compliance statement for WIS entities."
			MODULE -- this module
				GROUP wisORInfoGroup
					DESCRIPTION 
						"This group is for WIS systems."
			::= { wisSnmpGroups 2 }

		
		wisBridgeGroups OBJECT IDENTIFIER ::= { wisSnmpInfo 2 }

		
	
	END

--
-- WIS-MIB.my
--
