--
-- Accedian Enterprise Specific MIB
--
-- Copyright (c) 2005-2016, Accedian Networks, Inc.
-- All rights reserved.
--
-- The contents of this document are subject to change without notice.
--


ACD-REGULATOR-MIB DEFINITIONS ::= BEGIN

IMPORTS
    MODULE-IDENTITY, OBJECT-TYPE,
    Gauge32, Counter32, Counter64, Unsigned32
        FROM SNMPv2-SMI
    DisplayString, TruthValue, DateAndTime, RowStatus
        FROM SNMPv2-TC
    MODULE-COMPLIANCE, OBJECT-GROUP
        FROM SNMPv2-CONF
    acdMibs
        FROM ACCEDIAN-SMI;

acdRegulator MODULE-IDENTITY

    LAST-UPDATED "201702210100Z"
    ORGANIZATION "Accedian Networks, Inc."
    CONTACT-INFO
            "Accedian Technical Assistance Center
             Accedian Networks, Inc.
             2351 Alfred-Nobel blvd., Suite N-410
             Saint-Laurent, Quebec Canada H4S 2A9
             E-mail: support@accedian.com"
    DESCRIPTION
            "The Regulators database for this Accedian Networks device."

    REVISION "201702210100Z"        -- 21 February 2017
    DESCRIPTION
            "Change the Unit of acdRegulatorCbs and acdRegulatorEbs
             from Kbytes to KiB."

    REVISION "201609230100Z"        -- 23 September 2016
    DESCRIPTION
            "Add acdRegulatorHistStatsID and acdRegulatorHistStatsSampleIndex
             to acdRegulatorHistStatsGroup."

    REVISION "201605260100Z"        -- 26 May 2016
    DESCRIPTION
            "Set access level to read-only for acdRegulatorHistStatsID,
             acdRegulatorHistStatsSampleIndex."

    REVISION "201406090000Z"        -- 09 Jun 2014
    DESCRIPTION
            "Added Green, Yellow, Red Stats to acdRegulatorStatsEntry."
            
    REVISION "201312010000Z"        -- 01.Dec 2013
    DESCRIPTION
            "Added CIR-MAX, EIR-MAX to AcdRegulatorEntry."

    REVISION "201201100100Z"        -- 10 Jan 2012
    DESCRIPTION
            "Add acdRegulatorWorkingRate entry in acdRegulatorTable."
    REVISION "201110100100Z"        -- 10 October 2011
    DESCRIPTION
            "Add acdRegulatorTableLastChangeTid."

    REVISION "201011100100Z"        -- 10 November 2010
    DESCRIPTION
            "Add compliance section."

    REVISION "200805010100Z"        -- 1 May 2008
    DESCRIPTION
            "Add RowStatus in acdRegulatorTable table."

    REVISION "200802060100Z"        -- 6 Feb 2008
    DESCRIPTION
            "Add support for history table."

    REVISION "200703280100Z"        -- 28 March 2007
    DESCRIPTION
            "Initial version of MIB module ACD-REGULATOR-MIB."

    ::= { acdMibs 6 }

acdRegulatorNotifications   OBJECT IDENTIFIER ::= { acdRegulator 4 }
acdRegulatorMIBObjects      OBJECT IDENTIFIER ::= { acdRegulator 5 }
acdRegulatorConformance     OBJECT IDENTIFIER ::= { acdRegulator 6 }

acdRegulatorTableTid        OBJECT IDENTIFIER ::= { acdRegulatorMIBObjects 1 }

-----------------------------------------------------------------------
 -- The Regulators table
 -- This table contains all Regulators.
---------------------------------------------------------------------------

acdRegulatorTable OBJECT-TYPE
    SYNTAX      SEQUENCE OF AcdRegulatorEntry
    MAX-ACCESS  not-accessible
    STATUS      current
    DESCRIPTION
            "Table of all Regulators"
    ::= { acdRegulator 1 }

acdRegulatorEntry OBJECT-TYPE
    SYNTAX      AcdRegulatorEntry
    MAX-ACCESS  not-accessible
    STATUS      current
    DESCRIPTION
            "A Regulator is a two rates three colors engine to regulate a
             given traffic."
    INDEX   { acdRegulatorID }
    ::=  { acdRegulatorTable 1 }


AcdRegulatorEntry ::= SEQUENCE {
    acdRegulatorID              Unsigned32,
    acdRegulatorName            DisplayString,
    acdRegulatorCir             Unsigned32,
    acdRegulatorCbs             Unsigned32,
    acdRegulatorEir             Unsigned32,
    acdRegulatorEbs             Unsigned32,
    acdRegulatorIsBlind         TruthValue,
    acdRegulatorIsCouple        TruthValue,
    acdRegulatorRowStatus       RowStatus,
    acdRegulatorWorkingRate     INTEGER,
    acdRegulatorCirMax          Unsigned32,
    acdRegulatorEirMax          Unsigned32
}

acdRegulatorID  OBJECT-TYPE
    SYNTAX      Unsigned32
    MAX-ACCESS  not-accessible
    STATUS      current
    DESCRIPTION
        "Unique value for each regulator entry. Its value ranges from 1 to
        MAXINT (4 bytes). "
   ::= { acdRegulatorEntry 1 }

acdRegulatorName OBJECT-TYPE
    SYNTAX      DisplayString (SIZE (1..31))
    MAX-ACCESS  read-create
    STATUS      current
    DESCRIPTION
        "This is a string to identify the regulator."
    ::= { acdRegulatorEntry 2 }

acdRegulatorCir OBJECT-TYPE
    SYNTAX      Unsigned32
    UNITS       "Kbps"
    MAX-ACCESS  read-create
    STATUS      current
    DESCRIPTION
        "The committed information rate."
    DEFVAL      { 20000 }
   ::= { acdRegulatorEntry 3 }

acdRegulatorCbs OBJECT-TYPE
    SYNTAX      Unsigned32
    UNITS       "KiB"
    MAX-ACCESS  read-create
    STATUS      current
    DESCRIPTION
        "The committed burst size."
    DEFVAL      { 8 }
   ::= { acdRegulatorEntry 4 }

acdRegulatorEir OBJECT-TYPE
    SYNTAX      Unsigned32
    UNITS       "Kbps"
    MAX-ACCESS  read-create
    STATUS      current
    DESCRIPTION
        "The excess information rate."
    DEFVAL      { 1000 }
   ::= { acdRegulatorEntry 5 }

acdRegulatorEbs OBJECT-TYPE
    SYNTAX      Unsigned32
    UNITS       "KiB"
    MAX-ACCESS  read-create
    STATUS      current
    DESCRIPTION
        "The excess burst size."
    DEFVAL      { 8 }
   ::= { acdRegulatorEntry 6 }

acdRegulatorIsBlind OBJECT-TYPE
    SYNTAX      TruthValue
    MAX-ACCESS  read-create
    STATUS      current
    DESCRIPTION
        "Enable or disable the pre-marking color processing."
    DEFVAL      { false }
    ::= { acdRegulatorEntry 7 }

acdRegulatorIsCouple OBJECT-TYPE
    SYNTAX      TruthValue
    MAX-ACCESS  read-create
    STATUS      current
    DESCRIPTION
        "Enable or disable the coupling flag in this regulator."
    DEFVAL      { false }
    ::= { acdRegulatorEntry 8 }

acdRegulatorRowStatus OBJECT-TYPE
    SYNTAX      RowStatus
    MAX-ACCESS  read-create
    STATUS      current
    DESCRIPTION
       "All columns must have a valid value before a row can be activated. To
        create a new regulator you shall provide the a unique name for
        an empty row with the RowStatus set to Create and Go. To delete the
        row you need to set the RowStatus to destroy."
    ::= { acdRegulatorEntry 9 }

acdRegulatorWorkingRate OBJECT-TYPE
    SYNTAX      INTEGER {
                    layer1(1),
                    layer2(2)
    }
    MAX-ACCESS  read-only
    STATUS      current
    DESCRIPTION
        "The layer at which the regulator work. The layer-1 Ethernet Frame
         contains all Ethernet Frame fields plus the Inter-Frame Gap (IPG),
         Preamble and Start-Frame Delimiter (SFD). The layer-2 Ethernet
         Frame contains all Ethernet Frame fields."
    DEFVAL      { layer1 }
    ::= { acdRegulatorEntry 10 }

acdRegulatorCirMax OBJECT-TYPE
    SYNTAX      Unsigned32
    UNITS       "Kbps"
    MAX-ACCESS  read-create
    STATUS      current
    DESCRIPTION
        "The maximum committed information rate."
    DEFVAL      { 20000 }
   ::= { acdRegulatorEntry 11 }

acdRegulatorEirMax OBJECT-TYPE
    SYNTAX      Unsigned32
    UNITS       "Kbps"
    MAX-ACCESS  read-create
    STATUS      current
    DESCRIPTION
        "The maximum excess information rate."
    DEFVAL      { 1000 }
   ::= { acdRegulatorEntry 12 }

---------------------------------------------------------------------------
 -- The Regulator Counters table
 -- This table contains all counters associated with each regulator.
---------------------------------------------------------------------------

acdRegulatorStatsTable OBJECT-TYPE
    SYNTAX      SEQUENCE OF AcdRegulatorStatsEntry
    MAX-ACCESS  not-accessible
    STATUS      current
    DESCRIPTION
            "Table of all counters associated with each regulator."
    ::= { acdRegulator 2 }

acdRegulatorStatsEntry OBJECT-TYPE
    SYNTAX      AcdRegulatorStatsEntry
    MAX-ACCESS  not-accessible
    STATUS      current
    DESCRIPTION
            "An Entry consists of statitics related to a regulator entry."
    INDEX   { acdRegulatorStatsID }
    ::=  { acdRegulatorStatsTable 1 }


AcdRegulatorStatsEntry ::= SEQUENCE {
    acdRegulatorStatsID                     Unsigned32,
    acdRegulatorStatsAcceptOctets           Counter32,
    acdRegulatorStatsAcceptOverflowOctets   Counter32,
    acdRegulatorStatsAcceptHCOctets         Counter64,
    acdRegulatorStatsAcceptPkts             Counter32,
    acdRegulatorStatsAcceptOverflowPkts     Counter32,
    acdRegulatorStatsAcceptHCPkts           Counter64,
    acdRegulatorStatsAcceptRate             Gauge32,
    acdRegulatorStatsDropOctets             Counter32,
    acdRegulatorStatsDropOverflowOctets     Counter32,
    acdRegulatorStatsDropHCOctets           Counter64,
    acdRegulatorStatsDropPkts               Counter32,
    acdRegulatorStatsDropOverflowPkts       Counter32,
    acdRegulatorStatsDropHCPkts             Counter64,
    acdRegulatorStatsDropRate               Gauge32,
    acdRegulatorStatsGreenHCOctets          Counter64,
    acdRegulatorStatsGreenHCPkts            Counter64,
    acdRegulatorStatsYellowHCOctets         Counter64,
    acdRegulatorStatsYellowHCPkts           Counter64,
    acdRegulatorStatsRedHCOctets            Counter64,
    acdRegulatorStatsRedHCPkts              Counter64,
    acdRegulatorStatsGreenRate              Gauge32,
    acdRegulatorStatsYellowRate             Gauge32,
    acdRegulatorStatsRedRate                Gauge32
}

acdRegulatorStatsID  OBJECT-TYPE
    SYNTAX      Unsigned32
    MAX-ACCESS  not-accessible
    STATUS      current
    DESCRIPTION
        "Unique value for each regulator entry. Its value ranges from 1 to
        MAXINT (4 bytes)."
   ::= { acdRegulatorStatsEntry 1 }

acdRegulatorStatsAcceptOctets OBJECT-TYPE
    SYNTAX      Counter32
    UNITS       "Octets"
    MAX-ACCESS  read-only
    STATUS      current
    DESCRIPTION
        "The total number of octets received by this regulator. This is a
         32 bits counter. Combined with acdRegulatorStatsAcceptOverflowOctets,
         it provides the equivalent of the 64 bits counter
         acdRegulatorStatsAcceptHCOctets."
    ::= { acdRegulatorStatsEntry 2 }

acdRegulatorStatsAcceptOverflowOctets OBJECT-TYPE
    SYNTAX      Counter32
    MAX-ACCESS  read-only
    STATUS      current
    DESCRIPTION
        "The number of times the associated acdRegulatorStatsAcceptOctets
         counter has overflowed. This is a 32 bits counter. Combined with 
         acdRegulatorStatsAcceptOctets, it provides the equivalent of the
         64 bits counter acdRegulatorStatsAccpetHCOctets."
    ::= { acdRegulatorStatsEntry 3 }

acdRegulatorStatsAcceptHCOctets OBJECT-TYPE
    SYNTAX      Counter64
    UNITS       "Octets"
    MAX-ACCESS  read-only
    STATUS      current
    DESCRIPTION
        "The total number of octets received by this regulator."
    ::= { acdRegulatorStatsEntry 4 }

acdRegulatorStatsAcceptPkts OBJECT-TYPE
    SYNTAX      Counter32
    UNITS       "Packets"
    MAX-ACCESS  read-only
    STATUS      current
    DESCRIPTION
        "The total number of packets received by this regulator. This is a
         32 bits counter. Combined with acdRegulatorStatsAcceptOverflowPkts,
         it provides the equivalent of the 64 bits counter
         acdRegulatorStatsAcceptHCPkts."
    ::= { acdRegulatorStatsEntry 5 }

acdRegulatorStatsAcceptOverflowPkts OBJECT-TYPE
    SYNTAX      Counter32
    MAX-ACCESS  read-only
    STATUS      current
    DESCRIPTION
        "The number of times the associated acdRegulatorStatsAcceptPkts
         counter has overflowed. This is a 32 bits counter. Combined with 
         acdRegulatorStatsAcceptPkts, it provides the equivalent of the
         64 bits counter acdRegulatorStatsAcceptHCPkts."
    ::= { acdRegulatorStatsEntry 6 }

acdRegulatorStatsAcceptHCPkts OBJECT-TYPE
    SYNTAX      Counter64
    UNITS       "Packets"
    MAX-ACCESS  read-only
    STATUS      current
    DESCRIPTION
        "The total number of packets received by this regulator."
    ::= { acdRegulatorStatsEntry 7 }

acdRegulatorStatsAcceptRate OBJECT-TYPE
    SYNTAX      Gauge32
    UNITS       "Kbps"
    MAX-ACCESS  read-only
    STATUS      current
    DESCRIPTION
        "The accept rate."
    ::= { acdRegulatorStatsEntry 8 }

acdRegulatorStatsDropOctets OBJECT-TYPE
    SYNTAX      Counter32
    UNITS       "Octets"
    MAX-ACCESS  read-only
    STATUS      current
    DESCRIPTION
        "The total number of octets received by this regulator. This is a
         32 bits counter. Combined with acdRegulatorStatsDropOverflowOctets,
         it provides the equivalent of the 64 bits counter
         acdRegulatorStatsDropHCOctets."
    ::= { acdRegulatorStatsEntry 9 }

acdRegulatorStatsDropOverflowOctets OBJECT-TYPE
    SYNTAX      Counter32
    MAX-ACCESS  read-only
    STATUS      current
    DESCRIPTION
        "The number of times the associated acdRegulatorStatsDropOctets
         counter has overflowed. This is a 32 bits counter. Combined with 
         acdRegulatorStatsDropOctets, it provides the equivalent of the
         64 bits counter acdRegulatorStatsDropHCOctets."
    ::= { acdRegulatorStatsEntry 10 }

acdRegulatorStatsDropHCOctets OBJECT-TYPE
    SYNTAX      Counter64
    UNITS       "Octets"
    MAX-ACCESS  read-only
    STATUS      current
    DESCRIPTION
        "The total number of octets received by this regulator."
    ::= { acdRegulatorStatsEntry 11 }

acdRegulatorStatsDropPkts OBJECT-TYPE
    SYNTAX      Counter32
    UNITS       "Packets"
    MAX-ACCESS  read-only
    STATUS      current
    DESCRIPTION
        "The total number of packets received by this regulator. This is a
         32 bits counter. Combined with acdRegulatorStatsDropOverflowPkts,
         it provides the equivalent of the 64 bits counter
         acdRegulatorStatsDropHCPkts."
    ::= { acdRegulatorStatsEntry 12 }

acdRegulatorStatsDropOverflowPkts OBJECT-TYPE
    SYNTAX      Counter32
    MAX-ACCESS  read-only
    STATUS      current
    DESCRIPTION
        "The number of times the associated acdRegulatorStatsDropPkts
         counter has overflowed. This is a 32 bits counter. Combined with 
         acdRegulatorStatsDropPkts, it provides the equivalent of the
         64 bits counter acdRegulatorStatsDropHCPkts."
    ::= { acdRegulatorStatsEntry 13 }

acdRegulatorStatsDropHCPkts OBJECT-TYPE
    SYNTAX      Counter64
    UNITS       "Packets"
    MAX-ACCESS  read-only
    STATUS      current
    DESCRIPTION
        "The total number of packets received by this regulator."
    ::= { acdRegulatorStatsEntry 14 }

acdRegulatorStatsDropRate OBJECT-TYPE
    SYNTAX      Gauge32
    UNITS       "Kbps"
    MAX-ACCESS  read-only
    STATUS      current
    DESCRIPTION
        "The drop rate."
    ::= { acdRegulatorStatsEntry 15 }

acdRegulatorStatsGreenHCOctets OBJECT-TYPE
    SYNTAX      Counter64
    UNITS       "Octets"
    MAX-ACCESS  read-only
    STATUS      current
    DESCRIPTION
        "The total number of Green octets received by this regulator."
    ::= { acdRegulatorStatsEntry 16 }
    
acdRegulatorStatsGreenHCPkts OBJECT-TYPE
    SYNTAX      Counter64
    UNITS       "Packets"
    MAX-ACCESS  read-only
    STATUS      current
    DESCRIPTION
        "The total number of Green packets received by this regulator."
    ::= { acdRegulatorStatsEntry 17 }

acdRegulatorStatsYellowHCOctets OBJECT-TYPE
    SYNTAX      Counter64
    UNITS       "Octets"
    MAX-ACCESS  read-only
    STATUS      current
    DESCRIPTION
        "The total number of Yellow octets received by this regulator."
    ::= { acdRegulatorStatsEntry 18 }
    
acdRegulatorStatsYellowHCPkts OBJECT-TYPE
    SYNTAX      Counter64
    UNITS       "Packets"
    MAX-ACCESS  read-only
    STATUS      current
    DESCRIPTION
        "The total number of Yellow packets received by this regulator."
    ::= { acdRegulatorStatsEntry 19 }

acdRegulatorStatsRedHCOctets OBJECT-TYPE
    SYNTAX      Counter64
    UNITS       "Octets"
    MAX-ACCESS  read-only
    STATUS      current
    DESCRIPTION
        "The total number of Red octets received by this regulator."
    ::= { acdRegulatorStatsEntry 20 }
    
acdRegulatorStatsRedHCPkts OBJECT-TYPE
    SYNTAX      Counter64
    UNITS       "Packets"
    MAX-ACCESS  read-only
    STATUS      current
    DESCRIPTION
        "The total number of Red packets received by this regulator."
    ::= { acdRegulatorStatsEntry 21 }

acdRegulatorStatsGreenRate OBJECT-TYPE
    SYNTAX      Gauge32
    UNITS       "Kbps"
    MAX-ACCESS  read-only
    STATUS      current
    DESCRIPTION
        "The Green rate."
    ::= { acdRegulatorStatsEntry 22 }

acdRegulatorStatsYellowRate OBJECT-TYPE
    SYNTAX      Gauge32
    UNITS       "Kbps"
    MAX-ACCESS  read-only
    STATUS      current
    DESCRIPTION
        "The Yellow rate."
    ::= { acdRegulatorStatsEntry 23 }

acdRegulatorStatsRedRate OBJECT-TYPE
    SYNTAX      Gauge32
    UNITS       "Kbps"
    MAX-ACCESS  read-only
    STATUS      current
    DESCRIPTION
        "The Red rate."
    ::= { acdRegulatorStatsEntry 24 }
---------------------------------------------------------------------------
 -- The Regulator History group

 -- The Regulator History group records periodic statistical samples
 -- from a regulator and stores them for later retrieval.

---------------------------------------------------------------------------

acdRegulatorHistStatsTable OBJECT-TYPE
    SYNTAX      SEQUENCE OF AcdRegulatorHistStatsEntry
    MAX-ACCESS  not-accessible
    STATUS      current
    DESCRIPTION
            "Table of all counters associated with each regulator."
    ::= { acdRegulator 3 }

acdRegulatorHistStatsEntry OBJECT-TYPE
    SYNTAX      AcdRegulatorHistStatsEntry
    MAX-ACCESS  not-accessible
    STATUS      current
    DESCRIPTION
            "An Entry consists of statitics related to a regulator entry."
    INDEX   { acdRegulatorHistStatsID , acdRegulatorHistStatsSampleIndex }
    ::=  { acdRegulatorHistStatsTable 1 }


AcdRegulatorHistStatsEntry ::= SEQUENCE {
    acdRegulatorHistStatsID                     Unsigned32,
    acdRegulatorHistStatsSampleIndex            Unsigned32,
    acdRegulatorHistStatsStatus                 INTEGER,
    acdRegulatorHistStatsDuration               Unsigned32,
    acdRegulatorHistStatsIntervalEnd            DateAndTime,
    acdRegulatorHistStatsAcceptOctets           Counter32,
    acdRegulatorHistStatsAcceptOverflowOctets   Counter32,
    acdRegulatorHistStatsAcceptHCOctets         Counter64,
    acdRegulatorHistStatsAcceptPkts             Counter32,
    acdRegulatorHistStatsAcceptOverflowPkts     Counter32,
    acdRegulatorHistStatsAcceptHCPkts           Counter64,
    acdRegulatorHistStatsAcceptAvgRate          Gauge32,
    acdRegulatorHistStatsAcceptMinRate          Gauge32,
    acdRegulatorHistStatsAcceptMaxRate          Gauge32,
    acdRegulatorHistStatsDropOctets             Counter32,
    acdRegulatorHistStatsDropOverflowOctets     Counter32,
    acdRegulatorHistStatsDropHCOctets           Counter64,
    acdRegulatorHistStatsDropPkts               Counter32,
    acdRegulatorHistStatsDropOverflowPkts       Counter32,
    acdRegulatorHistStatsDropHCPkts             Counter64,
    acdRegulatorHistStatsDropAvgRate            Gauge32,
    acdRegulatorHistStatsDropMinRate            Gauge32,
    acdRegulatorHistStatsDropMaxRate            Gauge32,
    acdRegulatorHistStatsGreenHCOctets          Counter64,
    acdRegulatorHistStatsGreenHCPkts            Counter64,
    acdRegulatorHistStatsYellowHCOctets         Counter64,
    acdRegulatorHistStatsYellowHCPkts           Counter64,
    acdRegulatorHistStatsRedHCOctets            Counter64,
    acdRegulatorHistStatsRedHCPkts              Counter64,
    acdRegulatorHistStatsGreenAvgRate           Gauge32,
    acdRegulatorHistStatsGreenMinRate           Gauge32,
    acdRegulatorHistStatsGreenMaxRate           Gauge32,
    acdRegulatorHistStatsYellowAvgRate          Gauge32,
    acdRegulatorHistStatsYellowMinRate          Gauge32,
    acdRegulatorHistStatsYellowMaxRate          Gauge32,
    acdRegulatorHistStatsRedAvgRate             Gauge32,
    acdRegulatorHistStatsRedMinRate             Gauge32,
    acdRegulatorHistStatsRedMaxRate             Gauge32
}

acdRegulatorHistStatsID  OBJECT-TYPE
    SYNTAX      Unsigned32
    MAX-ACCESS  read-only
    STATUS      current
    DESCRIPTION
        "Unique value for each regulator entry. Its value ranges from 1 to
        MAXINT (4 bytes)."
    ::= { acdRegulatorHistStatsEntry 1 }

acdRegulatorHistStatsSampleIndex  OBJECT-TYPE
    SYNTAX      Unsigned32
    MAX-ACCESS  read-only
    STATUS      current
    DESCRIPTION
        "An index that uniquely identifies the particular sample this entry
         represents among all samples associated with the same regulator
         instance. This index starts at 1 and increases by one as each new
         sample."
    ::= { acdRegulatorHistStatsEntry 2 }

acdRegulatorHistStatsStatus OBJECT-TYPE
    SYNTAX      INTEGER {
                    valid(1),
                    invalid(2)
    }
    MAX-ACCESS  read-only
    STATUS      current
    DESCRIPTION
        "The status of this acdRegulatorHistStats entry."
    ::= { acdRegulatorHistStatsEntry 3 }

acdRegulatorHistStatsDuration  OBJECT-TYPE
    SYNTAX      Unsigned32
    MAX-ACCESS  read-only
    STATUS      current
    DESCRIPTION
        "The interval in seconds over which the data is sampled for this entry."
    ::= { acdRegulatorHistStatsEntry 4 }

acdRegulatorHistStatsIntervalEnd OBJECT-TYPE
    SYNTAX      DateAndTime
    MAX-ACCESS  read-only
    STATUS      current
    DESCRIPTION
       "This is the time of the end of this entry."
    ::= { acdRegulatorHistStatsEntry 5 }

acdRegulatorHistStatsAcceptOctets OBJECT-TYPE
    SYNTAX      Counter32
    UNITS       "Octets"
    MAX-ACCESS  read-only
    STATUS      current
    DESCRIPTION
        "The total number of octets received by this regulator during this
         sampling interval. This is a 32 bits counter. Combined with
         acdRegulatorHistStatsAcceptOverflowOctets, it provides the equivalent
         of the 64 bits counter acdRegulatorHistStatsAcceptHCOctets."
    ::= { acdRegulatorHistStatsEntry 6 }

acdRegulatorHistStatsAcceptOverflowOctets OBJECT-TYPE
    SYNTAX      Counter32
    MAX-ACCESS  read-only
    STATUS      current
    DESCRIPTION
        "The number of times the associated acdRegulatorHistStatsAcceptOctets
         counter has overflowed during this sampling interval. This is a
         32 bits counter. Combined with acdRegulatorHistStatsAcceptOctets,
         it provides the equivalent of the 64 bits counter
         acdRegulatorHistStatsAcceptHCOctets."
    ::= { acdRegulatorHistStatsEntry 7 }

acdRegulatorHistStatsAcceptHCOctets OBJECT-TYPE
    SYNTAX      Counter64
    UNITS       "Octets"
    MAX-ACCESS  read-only
    STATUS      current
    DESCRIPTION
        "The total number of octets received by this regulator during this
         sampling interval."
    ::= { acdRegulatorHistStatsEntry 8 }

acdRegulatorHistStatsAcceptPkts OBJECT-TYPE
    SYNTAX      Counter32
    UNITS       "Packets"
    MAX-ACCESS  read-only
    STATUS      current
    DESCRIPTION
        "The total number of packets received by this regulator during this
         sampling interval. This is a 32 bits counter. Combined with
         acdRegulatorHistStatsAcceptOverflowPkts, it provides the equivalent
         of the 64 bits counter acdRegulatorHistStatsAcceptHCPkts."
    ::= { acdRegulatorHistStatsEntry 9 }

acdRegulatorHistStatsAcceptOverflowPkts OBJECT-TYPE
    SYNTAX      Counter32
    MAX-ACCESS  read-only
    STATUS      current
    DESCRIPTION
        "The number of times the associated acdRegulatorHistStatsAcceptPkts
         counter has overflowed during this sampling interval. This is a
         32 bits counter. Combined with acdRegulatorHistStatsAcceptPkts, it
         provides the equivalent of the 64 bits counter
         acdRegulatorHistStatsAcceptHCPkts."
    ::= { acdRegulatorHistStatsEntry 10 }

acdRegulatorHistStatsAcceptHCPkts OBJECT-TYPE
    SYNTAX      Counter64
    UNITS       "Packets"
    MAX-ACCESS  read-only
    STATUS      current
    DESCRIPTION
        "The total number of packets received by this regulator during this
         sampling interval."
    ::= { acdRegulatorHistStatsEntry 11 }

acdRegulatorHistStatsAcceptAvgRate OBJECT-TYPE
    SYNTAX      Gauge32
    UNITS       "Kbps"
    MAX-ACCESS  read-only
    STATUS      current
    DESCRIPTION
        "The average accept rate during this sampling interval."
    ::= { acdRegulatorHistStatsEntry 12 }

acdRegulatorHistStatsAcceptMinRate OBJECT-TYPE
    SYNTAX      Gauge32
    UNITS       "Kbps"
    MAX-ACCESS  read-only
    STATUS      current
    DESCRIPTION
        "The minimum accept rate during this sampling interval."
    ::= { acdRegulatorHistStatsEntry 13 }

acdRegulatorHistStatsAcceptMaxRate OBJECT-TYPE
    SYNTAX      Gauge32
    UNITS       "Kbps"
    MAX-ACCESS  read-only
    STATUS      current
    DESCRIPTION
        "The maximum accept rate during this sampling interval."
    ::= { acdRegulatorHistStatsEntry 14 }

acdRegulatorHistStatsDropOctets OBJECT-TYPE
    SYNTAX      Counter32
    UNITS       "Octets"
    MAX-ACCESS  read-only
    STATUS      current
    DESCRIPTION
        "The total number of octets received by this regulator during this
         sampling interval. This is a 32 bits counter. Combined the overflow,
         counter it provides the equivalent of the 64 bits counter
         acdRegulatorHistStatsDropHCOctets."
    ::= { acdRegulatorHistStatsEntry 15 }

acdRegulatorHistStatsDropOverflowOctets OBJECT-TYPE
    SYNTAX      Counter32
    MAX-ACCESS  read-only
    STATUS      current
    DESCRIPTION
        "The number of times the associated acdRegulatorHistStatsDropOctets
         counter has overflowed during this sampling interval. This is a
         32 bits counter. Combined with acdRegulatorHistStatsDropOctets, it
         provides the equivalent of the 64 bits counter
         acdRegulatorHistStatsDropHCOctets."
    ::= { acdRegulatorHistStatsEntry 16 }

acdRegulatorHistStatsDropHCOctets OBJECT-TYPE
    SYNTAX      Counter64
    UNITS       "Octets"
    MAX-ACCESS  read-only
    STATUS      current
    DESCRIPTION
        "The total number of octets received by this regulator during this
         sampling interval."
    ::= { acdRegulatorHistStatsEntry 17 }

acdRegulatorHistStatsDropPkts OBJECT-TYPE
    SYNTAX      Counter32
    UNITS       "Packets"
    MAX-ACCESS  read-only
    STATUS      current
    DESCRIPTION
        "The total number of packets received by this regulator during this
         sampling interval. This is a 32 bits counter. Combined with
         acdRegulatorHistStatsDropOverflowPkts, it provides the equivalent of
         the 64 bits counter acdRegulatorHistStatsDropHCPkts."
    ::= { acdRegulatorHistStatsEntry 18 }

acdRegulatorHistStatsDropOverflowPkts OBJECT-TYPE
    SYNTAX      Counter32
    MAX-ACCESS  read-only
    STATUS      current
    DESCRIPTION
        "The number of times the associated acdRegulatorHistStatsDropPkts
         counter has overflowed during this sampling interval. This is a
         32 bits counter. Combined with acdRegulatorHistStatsDropPkts, it
         provides the equivalent of the 64 bits counter
         acdRegulatorHistStatsDropHCPkts."
    ::= { acdRegulatorHistStatsEntry 19 }

acdRegulatorHistStatsDropHCPkts OBJECT-TYPE
    SYNTAX      Counter64
    UNITS       "Packets"
    MAX-ACCESS  read-only
    STATUS      current
    DESCRIPTION
        "The total number of packets received by this regulator during this
         sampling interval."
    ::= { acdRegulatorHistStatsEntry 20 }

acdRegulatorHistStatsDropAvgRate OBJECT-TYPE
    SYNTAX      Gauge32
    UNITS       "Kbps"
    MAX-ACCESS  read-only
    STATUS      current
    DESCRIPTION
        "The average drop rate during this sampling interval."
    ::= { acdRegulatorHistStatsEntry 21 }

acdRegulatorHistStatsDropMinRate OBJECT-TYPE
    SYNTAX      Gauge32
    UNITS       "Kbps"
    MAX-ACCESS  read-only
    STATUS      current
    DESCRIPTION
        "The minimum drop rate during this sampling interval."
    ::= { acdRegulatorHistStatsEntry 22 }

acdRegulatorHistStatsDropMaxRate OBJECT-TYPE
    SYNTAX      Gauge32
    UNITS       "Kbps"
    MAX-ACCESS  read-only
    STATUS      current
    DESCRIPTION
        "The maximum drop rate during this sampling interval."
    ::= { acdRegulatorHistStatsEntry 23 }

acdRegulatorHistStatsGreenHCOctets OBJECT-TYPE
    SYNTAX      Counter64
    UNITS       "Octets"
    MAX-ACCESS  read-only
    STATUS      current
    DESCRIPTION
        "The total number of Green octets received by this regulator during this
         sampling interval."
    ::= { acdRegulatorHistStatsEntry 24 }    
    
acdRegulatorHistStatsGreenHCPkts OBJECT-TYPE
    SYNTAX      Counter64
    UNITS       "Packets"
    MAX-ACCESS  read-only
    STATUS      current
    DESCRIPTION
        "The total number of Green packets received by this regulator during this
         sampling interval."
    ::= { acdRegulatorHistStatsEntry 25 }

acdRegulatorHistStatsYellowHCOctets OBJECT-TYPE
    SYNTAX      Counter64
    UNITS       "Octets"
    MAX-ACCESS  read-only
    STATUS      current
    DESCRIPTION
        "The total number of Yellow octets received by this regulator during this
         sampling interval."
    ::= { acdRegulatorHistStatsEntry 26 }    
    
acdRegulatorHistStatsYellowHCPkts OBJECT-TYPE
    SYNTAX      Counter64
    UNITS       "Packets"
    MAX-ACCESS  read-only
    STATUS      current
    DESCRIPTION
        "The total number of Yellow packets received by this regulator during this
         sampling interval."
    ::= { acdRegulatorHistStatsEntry 27 }

acdRegulatorHistStatsRedHCOctets OBJECT-TYPE
    SYNTAX      Counter64
    UNITS       "Octets"
    MAX-ACCESS  read-only
    STATUS      current
    DESCRIPTION
        "The total number of Red octets received by this regulator during this
         sampling interval."
    ::= { acdRegulatorHistStatsEntry 28 }    
    
acdRegulatorHistStatsRedHCPkts OBJECT-TYPE
    SYNTAX      Counter64
    UNITS       "Packets"
    MAX-ACCESS  read-only
    STATUS      current
    DESCRIPTION
        "The total number of Red packets received by this regulator during this
         sampling interval."
    ::= { acdRegulatorHistStatsEntry 29 }
    

acdRegulatorHistStatsGreenAvgRate OBJECT-TYPE
    SYNTAX      Gauge32
    UNITS       "Kbps"
    MAX-ACCESS  read-only
    STATUS      current
    DESCRIPTION
        "The average green rate during this sampling interval."
    ::= { acdRegulatorHistStatsEntry 30 }

acdRegulatorHistStatsGreenMinRate OBJECT-TYPE
    SYNTAX      Gauge32
    UNITS       "Kbps"
    MAX-ACCESS  read-only
    STATUS      current
    DESCRIPTION
        "The minimum green rate during this sampling interval."
    ::= { acdRegulatorHistStatsEntry 31 }

acdRegulatorHistStatsGreenMaxRate OBJECT-TYPE
    SYNTAX      Gauge32
    UNITS       "Kbps"
    MAX-ACCESS  read-only
    STATUS      current
    DESCRIPTION
        "The maximum green rate during this sampling interval."
    ::= { acdRegulatorHistStatsEntry 32 }

acdRegulatorHistStatsYellowAvgRate OBJECT-TYPE
    SYNTAX      Gauge32
    UNITS       "Kbps"
    MAX-ACCESS  read-only
    STATUS      current
    DESCRIPTION
        "The average Yellow rate during this sampling interval."
    ::= { acdRegulatorHistStatsEntry 33 }

acdRegulatorHistStatsYellowMinRate OBJECT-TYPE
    SYNTAX      Gauge32
    UNITS       "Kbps"
    MAX-ACCESS  read-only
    STATUS      current
    DESCRIPTION
        "The minimum Yellow rate during this sampling interval."
    ::= { acdRegulatorHistStatsEntry 34 }

acdRegulatorHistStatsYellowMaxRate OBJECT-TYPE
    SYNTAX      Gauge32
    UNITS       "Kbps"
    MAX-ACCESS  read-only
    STATUS      current
    DESCRIPTION
        "The maximum Yellow rate during this sampling interval."
    ::= { acdRegulatorHistStatsEntry 35 }
    
acdRegulatorHistStatsRedAvgRate OBJECT-TYPE
    SYNTAX      Gauge32
    UNITS       "Kbps"
    MAX-ACCESS  read-only
    STATUS      current
    DESCRIPTION
        "The average Red rate during this sampling interval."
    ::= { acdRegulatorHistStatsEntry 36 }

acdRegulatorHistStatsRedMinRate OBJECT-TYPE
    SYNTAX      Gauge32
    UNITS       "Kbps"
    MAX-ACCESS  read-only
    STATUS      current
    DESCRIPTION
        "The minimum Red rate during this sampling interval."
    ::= { acdRegulatorHistStatsEntry 37 }

acdRegulatorHistStatsRedMaxRate OBJECT-TYPE
    SYNTAX      Gauge32
    UNITS       "Kbps"
    MAX-ACCESS  read-only
    STATUS      current
    DESCRIPTION
        "The maximum Red rate during this sampling interval."
    ::= { acdRegulatorHistStatsEntry 38 }
---------------------------------------------------------------------------
 -- Transaction ID Information
---------------------------------------------------------------------------

acdRegulatorTableLastChangeTid OBJECT-TYPE
    SYNTAX      Unsigned32
    MAX-ACCESS  read-only
    STATUS      current
    DESCRIPTION
       "This is the transaction ID of the last change of the acdRegulatorTable
        table.  If this value is different since the last read this is indicate 
        a table change."
    ::= { acdRegulatorTableTid 1 }

---------------------------------------------------------------------------
 -- ACD-REGULATOR-MIB Module - Conformance Information
---------------------------------------------------------------------------

acdRegulatorCompliances  OBJECT IDENTIFIER ::= { acdRegulatorConformance 1 }
acdRegulatorGroups       OBJECT IDENTIFIER ::= { acdRegulatorConformance 2 }

---------------------------------------------------------------------------
 -- Units of conformance
---------------------------------------------------------------------------

acdRegulatorGroup OBJECT-GROUP
    OBJECTS {
        acdRegulatorName,
        acdRegulatorCir,
        acdRegulatorCbs,
        acdRegulatorEir,
        acdRegulatorEbs,
        acdRegulatorIsBlind,
        acdRegulatorIsCouple,
        acdRegulatorRowStatus,
        acdRegulatorWorkingRate,
        acdRegulatorCirMax,
        acdRegulatorEirMax
    }
    STATUS      current
    DESCRIPTION
       "Objects for the Regulator configurtion Group."
    ::= { acdRegulatorGroups 1 }

acdRegulatorStatsGroup OBJECT-GROUP
    OBJECTS {
        acdRegulatorStatsAcceptOctets,
        acdRegulatorStatsAcceptOverflowOctets,
        acdRegulatorStatsAcceptHCOctets,
        acdRegulatorStatsAcceptPkts,
        acdRegulatorStatsAcceptOverflowPkts,
        acdRegulatorStatsAcceptHCPkts,
        acdRegulatorStatsAcceptRate,
        acdRegulatorStatsDropOctets,
        acdRegulatorStatsDropOverflowOctets,
        acdRegulatorStatsDropHCOctets,
        acdRegulatorStatsDropPkts,
        acdRegulatorStatsDropOverflowPkts,
        acdRegulatorStatsDropHCPkts,
        acdRegulatorStatsDropRate,
        acdRegulatorStatsGreenHCOctets,
        acdRegulatorStatsGreenHCPkts,
        acdRegulatorStatsYellowHCOctets,
        acdRegulatorStatsYellowHCPkts,
        acdRegulatorStatsRedHCOctets,
        acdRegulatorStatsRedHCPkts,
        acdRegulatorStatsGreenRate,
        acdRegulatorStatsYellowRate,
        acdRegulatorStatsRedRate
    }
    STATUS      current
    DESCRIPTION
       "Objects for the Regulator statistics Group."
    ::= { acdRegulatorGroups 2 }

acdRegulatorHistStatsGroup OBJECT-GROUP
    OBJECTS {
        acdRegulatorHistStatsID,
        acdRegulatorHistStatsSampleIndex,
        acdRegulatorHistStatsStatus,
        acdRegulatorHistStatsDuration,
        acdRegulatorHistStatsIntervalEnd,
        acdRegulatorHistStatsAcceptOctets,
        acdRegulatorHistStatsAcceptOverflowOctets,
        acdRegulatorHistStatsAcceptHCOctets,
        acdRegulatorHistStatsAcceptPkts,
        acdRegulatorHistStatsAcceptOverflowPkts,
        acdRegulatorHistStatsAcceptHCPkts,
        acdRegulatorHistStatsAcceptAvgRate,
        acdRegulatorHistStatsAcceptMinRate,
        acdRegulatorHistStatsAcceptMaxRate,
        acdRegulatorHistStatsDropOctets,
        acdRegulatorHistStatsDropOverflowOctets,
        acdRegulatorHistStatsDropHCOctets,
        acdRegulatorHistStatsDropPkts,
        acdRegulatorHistStatsDropOverflowPkts,
        acdRegulatorHistStatsDropHCPkts,
        acdRegulatorHistStatsDropAvgRate,
        acdRegulatorHistStatsDropMinRate,
        acdRegulatorHistStatsDropMaxRate,
        acdRegulatorHistStatsGreenHCOctets,
        acdRegulatorHistStatsGreenHCPkts,
        acdRegulatorHistStatsYellowHCOctets,
        acdRegulatorHistStatsYellowHCPkts,
        acdRegulatorHistStatsRedHCOctets,
        acdRegulatorHistStatsRedHCPkts,
        acdRegulatorHistStatsGreenAvgRate,
        acdRegulatorHistStatsGreenMinRate,
        acdRegulatorHistStatsGreenMaxRate,
        acdRegulatorHistStatsYellowAvgRate,
        acdRegulatorHistStatsYellowMinRate,
        acdRegulatorHistStatsYellowMaxRate,
        acdRegulatorHistStatsRedAvgRate,
        acdRegulatorHistStatsRedMinRate ,
        acdRegulatorHistStatsRedMaxRate
    }
    STATUS      current
    DESCRIPTION
       "Objects for the Regulator history statistics Group."
    ::= { acdRegulatorGroups 3 }

acdRegulatorTidGroup OBJECT-GROUP
    OBJECTS {
        acdRegulatorTableLastChangeTid
    }
    STATUS      current
    DESCRIPTION
       "List of scalars to monitior changes in tables."
    ::= { acdRegulatorGroups 4 }

acdRegulatorCompliance MODULE-COMPLIANCE
    STATUS      current
    DESCRIPTION
       "The compliance statement for support of the ACD-REGULATOR-MIB module."
    MODULE
        MANDATORY-GROUPS {
            acdRegulatorGroup,
            acdRegulatorStatsGroup,
            acdRegulatorHistStatsGroup,
            acdRegulatorTidGroup
         }

    OBJECT  acdRegulatorRowStatus
      SYNTAX       RowStatus { active(1) }
      WRITE-SYNTAX RowStatus { createAndGo(4), destroy(6) }
      DESCRIPTION "Support for createAndWait is not required."

    ::= { acdRegulatorCompliances 1 }


END
